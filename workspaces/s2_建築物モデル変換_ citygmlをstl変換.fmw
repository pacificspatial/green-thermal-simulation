FME workspace s2_建築物モデル変換_ citygmlをstl変換.fmw
History: 2026-01-07,Takashi Iijima,LOD1建築物モデル底部の地形起伏によるクリップ処理追加

Parameters:
- SourceDataset_OGCGEOPACKAGE = $(FME_MF_DIR_USERTYPED)source\シミュレーション範囲 Dissolved.gpkg   # Simulation Extents [GeoPackage]
- SourceDataset_CITYGML = ""$(FME_MF_DIR)source\13101_chiyoda-ku_pref_2023_citygml_2_op\udx\bldg\53394620_bldg_6697_op.gml" "$(FME_MF_DIR)source\13101_chiyoda-ku_pref_2023_citygml_2_op\udx\bldg\53394621_bldg_6697_op.gml""   # Source CityGML File(s) [bldg]
- SourceDataset_CSV2 = $(FME_MF_DIR)output\offset_values.csv   # Source CSV File [offset_values]
- SourceDataset_STL = ""$(FME_MF_DIR)output\stl\ground.stl" "$(FME_MF_DIR)output\stl\road.stl" "$(FME_MF_DIR)output\stl\water.stl""   # Source STL Files [ground, road, water]
- DEST_COORDSYS = EPSG:6677
- DestDataset_STL = $(FME_MF_DIR_USERTYPED)output   # Destination Root Folder

Readers:
- OGCGEOPACKAGE_1: OGCGEOPACKAGE from $(SourceDataset_OGCGEOPACKAGE)
- CITYGML_1: CITYGML from $(SourceDataset_CITYGML)
- CSV2_1: CSV2 from $(SourceDataset_CSV2)
- STL_2: STL from $(SourceDataset_STL)

Writers:
- STL_1: STL to $(DestDataset_STL)

Note: シミュレーション範囲をカバーする3次メッシュ区画のメッシュコード / 53394620 / 53394621
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_bldg_data_quality_attribute{} xml_xml, uro_bldg_disaster_risk_attribute{} xml_xml, uro_bldg_dm_attribute{} xml_xml, uro_bldg_facility_attribute{} xml_xml, uro_bldg_facility_id_attribute{} xml_xml, uro_bldg_facility_type_attribute{} xml_xml, uro_bldg_key_value_pair_attribute{} xml_xml, uro_bldg_real_estate_idattribute{} xml_xml, uro_bldg_usecase_attribute{} xml_xml, uro_building_detail_attribute{} xml_xml, uro_building_idattribute{} xml_xml, uro_ifc_building_attribute{} xml_xml, uro_indoor_building_attribute{} xml_xml, uro_large_customer_facility_attribute{} xml_xml, 13+区市町村コード+大字・町コード+町・丁目コード xml_buffer, 地区計画 xml_buffer, 大字・町コード xml_buffer, 延べ面積換算係数 xml_buffer, 町・丁目コード xml_buffer, 説明注記 xml_buffer,
      再開発等促進区を定める地区計画 xml_buffer
    -> CsmapReprojector_2
Note: シミュレーション範囲内の全ての建築物がLOD0, LOD1 モデルを持っていることを前提とする。
CsmapReprojector_2
    DEST = $(DEST_COORDSYS)
    INTERPOLATION_TYPE_NAME = NearestNeighbor
    RASTER_CELL_SIZE = PreserveCells
    RASTER_TOLERANCE = 0.0
    REPROJECTED -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(_geometry_label) BEGINS_WITH lod0",LOD0,"BOOL_OP,OR,COMPOSITE_TEST,""""""1"""""",TEST_CLAUSE,CASE_INSENSITIVE_TEST @Value(_geometry_label) BEGINS_WITH lod1",LOD1,"BOOL_OP,OR,COMPOSITE_TEST,""""""1"""""",TEST_CLAUSE,CASE_INSENSITIVE_TEST @Value(_geometry_label) BEGINS_WITH lod2",LOD2
    LOD1 -> FeatureJoiner_LOD1 [LEFT]
    LOD0 -> Junction
Note: 2DForcer : Input
Junction
    -> Junction_2
Note: TestFilter : LOD0
Junction_2
    -> 2DForcer
2DForcer
    2D -> SpatialFilter [Candidate]
Note: シミュレーション範囲 / [OGCGEOPACKAGE]
parsed (reader OGCGEOPACKAGE_1)
    attributes: felt:feature int, felt:has_geometry boolean, felt:h3_index int, felt:geometry_size int, felt:color text, felt:fillOpacity double, felt:id text, felt:locked int, felt:ordering int, felt:showArea int, felt:strokeOpacity int, felt:strokeStyle text, felt:strokeWidth int, felt:type text, gpkg_fid int,PrimaryKey
    -> CsmapReprojector
CsmapReprojector
    DEST = $(DEST_COORDSYS)
    INTERPOLATION_TYPE_NAME = NearestNeighbor
    RASTER_CELL_SIZE = PreserveCells
    RASTER_TOLERANCE = 0.0
    SOURCE = EPSG:6668
    REPROJECTED -> SpatialFilter [Filter]
SpatialFilter
    AGGREGATE_HANDLING = Yes
    BASE_TYPE = Multiple Filters
    CURVE_BOUNDARY_RULE_PARAM = Default Rule
    PASS_CRITERIA = Pass Against One Filter
    PREDATTR = _predicate
    PREDICATES = CONTAINS
    USE_BOUNDING_BOX = No
    PASSED -> FeatureJoiner_LOD1 [RIGHT]
offset_values (reader CSV2_1)
    attributes: x_offset uint32, y_offset uint32, z_offset uint32
    -> FeatureMerger [SUPPLIER]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter
Offsetter
    MODE_LOOKUP = CARTESIAN
    XOFF = @Value(x_offset)
    YOFF = @Value(y_offset)
    ZOFF = @Value(z_offset)
    MODE = Cartesian Coordinate
    OFFSET -> BoundsExtractor
    OFFSET -> building_lod1 (writer STL_1)
building_lod1 (writer STL_1)
ground (reader STL_2)
    -> MeshMerger
road (reader STL_2)
    -> MeshMerger
water (reader STL_2)
    -> MeshMerger
MeshMerger
    ACCUM_INPUT_ATTRS_LOOKUP = One
    ACCUM_INPUT_ATTRS = Use Attributes From One Feature
    MESH -> BRepSolidBoundaryCreator.Beta [Surface]
BRepSolidBoundaryCreator.Beta
    ELEVATION = -100
    Top -> GeometryPartExtractor
    Side -> GeometryPartExtractor
    Bottom -> GeometryPartExtractor
Note: 個別の面を Face として抽出
GeometryPartExtractor
    GQUERY:
      for $geom in //geometry
      where $geom/@fme_geometry_type = 'Mesh Part'
      or $geom/@fme_geometry_type = 'IFMEFace'
      return number($geom/@fme_id)
    EXTRACTED -> Aggregator
Note: Faces -> MultiSurface
Aggregator
    ACCUM_ATTRS = None
    AGGREGATE_TYPE = Homogeneous Collection (If Possible)
    MODE = Geometry - Assemble One Level
    SEP = ,
    AGGREGATE -> GeometryCoercer
Note: ->CompositeSurface
GeometryCoercer
    GQUERY:
      for $geom in //geometry
      where $geom/count(parent::geometry) = 0
      return number($geom/@fme_id)
    KIND = fme_composite_surface
    COERCED -> GeometryCoercer_2
Note: ->BrepSolid
GeometryCoercer_2
    GQUERY:
      for $geom in //geometry
      where $geom/count(parent::geometry) = 0
      return number($geom/@fme_id)
    KIND = fme_brep_solid
    COERCED -> Clipper [CLIPPER]
Note: 地形起伏より下の部分を切り取る
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> building_lod1_clipped (writer STL_1)
building_lod1_clipped (writer STL_1)
Note: 建物の底面を除外する場合は Extruder の直後にこれを挿入する。
GeometryCoercer_3
    GQUERY:
      for $geom in //geometry
      where $geom/count(parent::geometry) = 0
      return number($geom/@fme_id)
    KIND = fme_composite_surface

Bookmark: シミュレーション範囲内のモデルを抽出
FeatureJoiner_LOD1
    ATTR_CONFLICT_RES = USE_LEFT
    GEOMETRY_HANDLING = USE_LEFT
    JOIN_KEYS = gml_id gml_id AUTO
    JOIN_MODE = Inner
    JOINED -> FeatureMerger [REQUESTOR]

Bookmark: 底部全面が地形起伏で切り取られるように, 底面の標高を5m下げた浮きがないLOD1立体を再作成する
BoundsExtractor
    ZMAX = _zmax
    ZMIN = _zmin
    -> SurfaceFootprintReplacer
SurfaceFootprintReplacer
    OFFSET_Z_LOOKUP = @Value(_zmin)-5
    SHADOW_TYPE = OVERHEAD
    OFFSET_Z = @Value(_zmin)-5
    SHADOW_MODE = Overhead Shadow
    FOOTPRINT -> Extruder
Extruder
    DIRECTION_LOOKUP = VERTICAL
    DISTANCE = (@Value(_zmax)-@Value(_zmin))+5
    DIRECTION = Vertical
    EXTRUDED -> Clipper [CANDIDATE]

FME custom transformer BRepSolidBoundaryCreator.Beta
Creates a planar surface representing the orthogonal projection of the source surface, and a ring-shaped vertical sidewall surface that bridges between the boundaries of the planar surface and the source surface. The resulting surfaces can be used to build a boundary representation solid (IFMEBRepSolid). 
    This transformer accepts features having a surface geometry except aggregate and multi-surface. If the input feature geometry is not acceptable, it will be output via the <Rejected> port. 
    Note: This transformer is a tech preview regarding surface manipulation with Python FME Objects API. It may be removed from the FME Hub if a regular transformer having a functionality equivalent to this transformer would be introduced in the future.
    Usage Note
    This transformer assumes that the source surface represents a single consecutive shape oriented to Z positive direction, and the boundary of the source surface is equal to the boundary of the orthogonal projection (i.e. the source surface is NOT folded). Otherwise, the translation could be aborted with an error or the resulting surfaces may not form a topologically clean solid. 
    You can transform an aggregate of surfaces which are output from this transformer into a boundary representation solid (IFMEBrepSolid) or a composite surface (IFMECompositeSurface), using an Aggregator and a GeometryCoercer transformer (Geometry Type: fme_brep_solid or fme_composite_surface).
    Output Ports 
    Top
    : 
    If the elevation which is specified through the "Planar Surface Elevation" parameter is less than the MINIMUM Z of the source surface, the source surface will be output via this port without any transformation. If the specified elevation is greater than the MAXIMUM Z of the source surface, a planar surface representing the orthogonal projection of the source surface will be output via this port.
    Side
    :
    A composite surface forming a ring-shaped vertical sidewall that bridges between the boundaries of the Top surface and the Bottom surface will be output via this port.
    Bottom
    :
    If the elevation which is specified through the "Planar Surface Elevation" parameter is less than the MINIMUM Z of the source surface, the planar surface representing the orthogonal projection of the source surface will be output via this port. If the specified elevation is greater than the MAXIMUM Z of the source surface, the source surface whose orientation is reversed will be output via this port.
Parameters
    Planar Surface Elevation
    :
    Specify the elevation of the planar surface which should be created as an orthogonal projection of the source surface. The value must be less than the MINIMUM Z, or greater than the MAXIMUM Z of the source surface. Otherwise, the input feature will be output via the <Rejected> port.

Parameters:
- ELEVATION =   # Planar Surface Elevation

Surface (input)
    -> AggregateFilter
AggregateFilter
    AGGREGATE -> AttributeCreator_3
    NOT_AGGREGATE -> GeometryFilter
GeometryFilter
    BREAK_AGG_BOOL = 0
    GEOM_PORTS = SURFACE
    BREAK_AGG = No
    GEOM_PORT_NAMES = Surface
    SURFACE -> BoundsExtractor
    <UNFILTERED> -> AttributeCreator_3
BoundsExtractor
    ZMAX = __ssc.zmax
    ZMIN = __ssc.zmin
    -> AttributeCreator
AttributeCreator
    ATTR_TABLE:
      SET_TO __ssc.elevation = $(ELEVATION)
      SET_TO __ssc.flag = FME_CONDITIONAL:DEFAULT_VALUE'0'BOOL_OP;OR;COMPOSITE_TEST;<Unused>;TEST $(ELEVATION) < @Value(__ssc.zmin)'-1'BOOL_OP;OR;COMPOSITE_TEST;<Unused>;TEST @Value(__ssc.zmax) < $(ELEVATION)'1'FME_NUM_CONDITIONS3___
    -> Tester
Tester
    BOOL_OP = OR
    TEST_CLAUSE = TEST @Value(__ssc.flag) != 0
    TEST_MODE = Automatic
    PASSED -> Counter
    FAILED -> AttributeCreator_2
Counter
    CNT_ATTR = __ssc.id
    DOMAIN = counter_id
    SCOPE = Local
    START = 0
    SCOPEVAR = Local
    -> Tester_2
    -> PythonCaller
Tester_2
    BOOL_OP = OR
    TEST_CLAUSE = TEST @Value(__ssc.flag) < 0
    TEST_MODE = Automatic
    PASSED -> Tester_3_PASSED
    FAILED -> Orientor
Note: Top
Tester_3_PASSED: Junction
    -> Top_2
Top_2: Junction
    -> Top (output)
Orientor
    FLIP_APPEARANCES_LOOKUP = FLIP_APPEARANCES
    KIND = REVERSE
    FLIP_APPEARANCES_CHOICE = Yes
    ORIENTED -> Tester_3_FAILED
Note: Bottom
Tester_3_FAILED: Junction
    -> Bottom_2
Bottom_2: Junction
    -> Bottom (output)
PythonCaller
    NEW_ATTRIBUTES = __ssc.id
    PYTHONSOURCE:
      # 2016-09-16, Takashi Iijima, Original Implementation

      import fme
      import fmeobjects

      class OutershellChopper(object):
          def input(self, feature):
              flag = int(feature.getAttribute('__ssc.flag'))
              self.chopped = []
              self.chop(feature.getGeometry())
              segs = {}
              for line in self.chopped:
                  coords = sorted([p.getXYZ() for p in line.getPoints()])
                  segs.setdefault((coords[0], coords[1]), []).append(line)
              for line in [s[0] for s in segs.values() if len(s) == 1]:
                  if flag < 0:
                      line.reverse()
                  feature.setGeometry(line)
                  self.pyoutput(feature)

          def chop(self, surface):
              if isinstance(surface, fmeobjects.FMEFace):
                  self.chopped += surface.getAsWireFrame()
              elif isinstance(surface, fmeobjects.FMEMesh):
                  self.chopped += surface.getAsWireFrame()
              elif isinstance(surface, fmeobjects.FMERectangleFace):
                  self.chop(surface.getAsFaceCopy())
              elif isinstance(surface, fmeobjects.FMETriangleFan):
                  for i in range(surface.numParts()):
                      self.chop(surface.getAsFaceAt(i))
              elif isinstance(surface, fmeobjects.FMETriangleStrip):
                  for i in range(surface.numParts()):
                      self.chop(surface.getAsFaceAt(i))
              elif isinstance(surface, fmeobjects.FMECompositeSurface):
                  for i in range(surface.numParts()):
                      self.chop(surface.getPartAt(i))
    PYTHONSYMBOL = OutershellChopper
    -> LineJoiner
LineJoiner
    ACCUM_ATTRS = ONE
    CLOSE = yes
    CONSIDER_NODE_ELEVATION_LOOKUP = YES
    GROUP_BY = __ssc.id
    LINES_AS_SEGMENTS = Yes
    NODED = END_NODED
    PRESERVE = yes
    ACCUM_ATTRS_NAME = Get Attributes From One Representative Feature
    BREAK = no
    CONSIDER_NODE_ELEVATION = yes
    TOPOLOGY = End noded
    LINE -> Counter_2
Counter_2
    CNT_ATTR = __ssc.part_id
    DOMAIN = counter_part_id
    SCOPE = Local
    START = 0
    SCOPEVAR = Local
    -> PathSplitter
PathSplitter
    -> PythonCaller_2
PythonCaller_2
    NEW_ATTRIBUTES = __ssc.type
    PYTHONSOURCE:
      # 2016-09-16: Takashi Iijima, Original Implementation

      import fme
      import fmeobjects
      class BRepSolidBoundaryCreator(object):
          def __init__(self):
              self.wallFaces = {}
              self.planarBoundaries = {}
              self.prevId = None
              self.feature = None

          def input(self, feature):
              id = feature.getAttribute('__ssc.id')
              if id != self.prevId:
                  self.outputSurface()
                  self.wallFaces = {}
                  self.planarBoundaries = {}
                  self.prevId = id
              partId = feature.getAttribute('__ssc.part_id')
              if partId not in self.wallFaces:
                  self.wallFaces[partId] = []
                  self.planarBoundaries[partId] = []
              v0 = feature.getCoordinate(0)
              v1 = feature.getCoordinate(1)
              if v0[0] != v1[0] or v0[1] != v1[1]:
                  z = float(feature.getAttribute('__ssc.elevation'))
                  v2 = (v1[0], v1[1], z)
                  v3 = (v0[0], v0[1], z)
                  boundary = fmeobjects.FMELine([v0, v1, v2, v3, v0])
                  self.wallFaces[partId].append(fmeobjects.FMEFace(boundary, fmeobjects.FME_CLOSE_3D_AVERAGE_MODE))
                  self.planarBoundaries[partId].append(v2)
                  self.feature = feature

          def close(self):
              self.outputSurface()

          def outputSurface(self):
              for partId in sorted(self.wallFaces.keys()):
                  wallFaces = self.wallFaces[partId]
                  planarBoundaries = self.planarBoundaries[partId]
                  if wallFaces:
                      sidewall = fmeobjects.FMECompositeSurface()
                      for face in wallFaces:
                          sidewall.appendPart(face)
                      self.feature.setGeometry(sidewall)
                      self.feature.setAttribute('__ssc.type', 'side')
                      self.pyoutput(self.feature)

                      planarBoundaries.append(planarBoundaries[0])
                      planar = fmeobjects.FMEPolygon(fmeobjects.FMELine(planarBoundaries))
                      self.feature.setGeometry(planar)
                      self.feature.setAttribute('__ssc.type', 'planar')
                      self.pyoutput(self.feature)
    PYTHONSYMBOL = BRepSolidBoundaryCreator
    -> Tester_3
Tester_3
    BOOL_OP = OR
    TEST_CLAUSE = TEST @Value(__ssc.type) = side
    TEST_MODE = Automatic
    PASSED -> Side (output)
    FAILED -> DonutBuilder
Side (output)
DonutBuilder
    ALLOW_CYCLES = No
    CONNECT_Z_MODE_LOOKUP = FIRST_WINS
    GROUP_BY = __ssc.id
    TAG_HOLES = NO
    CONNECT_Z_MODE = First Wins
    DROP = yes
    AREA -> FaceReplacer
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> Tester_4
Tester_4
    BOOL_OP = OR
    TEST_CLAUSE = TEST 0 < @Value(__ssc.flag)
    TEST_MODE = Automatic
    PASSED -> Top (output)
    FAILED -> Bottom (output)
Top (output)
Bottom (output)
AttributeCreator_2
    ATTR_TABLE = SET_TO _rejected_reason = specified elevation is within zmin and zmax of seed surface
    -> <Rejected> (output)
AttributeCreator_3
    ATTR_TABLE = SET_TO _rejected_reason = unsupported geometry type
    -> <Rejected> (output)
<Rejected> (output)
