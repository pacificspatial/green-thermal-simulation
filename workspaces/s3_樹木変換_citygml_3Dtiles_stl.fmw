FME workspace s3_樹木変換_citygml_3Dtiles_stl.fmw
Title: 大丸有樹木CityGMLおよび3DTiles作成_20250925
History: 2025-10-02,FREE 飯嶋,LOD1,LOD2ジオメトリおよびCityGMLネイティブの主題属性をCityGML形式で出力

Parameters:
- DestDataset_CITYGML = $(FME_MF_DIR_USERTYPED)output\udx\veg   # CityGML出力先フォルダー (*/udx/veg)
- CITYGML_OUT_ADE_XSD_DOC_CITYGML_3 = $(FME_MF_DIR_USERTYPED)resources\schemas\iur\uro\3.2\urbanObject.xsd   # i-UR 3.2 スキーマ (urbanObject.xsd)
- CITYGML_OUT_SCHEMA_LOCATION_CITYGML_3 = http://www.opengis.net/gml http://schemas.opengis.net/gml/3.1.1/base/gml.xsd http://www.opengis.net/citygml/profiles/base/2.0 http://schemas.opengis.net/citygml/profiles/base/2.0/CityGML.xsd https://www.geospatial.jp/iur/uro/3.2 ../../schemas/iur/uro/3.2/urbanObject.xsd   # xsi:schemaLocation
- CITYGML_OUT_SRS_NAME_CITYGML_3 = http://www.opengis.net/def/crs/EPSG/0/6697   # GML srsName
- PROJECTION_COORDSYS = EPSG:6677   # "" Projection Coordinate System
- CODELISTS = ../../codelists   # codelists path
- DestDataset_CESIUM3DTILES = $(FME_MF_DIR_USERTYPED)\output\3dtiles   # Destination Cesium 3D Tiles Folder
- SourceDataset_CSV2 = $(FME_MF_DIR_USERTYPED)\source\tree_20230214_for_citygml_20251117.csv   # Source CSV (Comma Separated Value) File(s)
- SourceDataset_OGCGEOPACKAGE = $(FME_MF_DIR_USERTYPED)source\シミュレーション範囲 Dissolved.gpkg   # GeoPackage File
- DestDataset_STL = $(FME_MF_DIR_USERTYPED)\output\stl   # Destination STL Folder
- DEST_COORDSYS = EPSG:6677
- SourceDataset_STL = $(FME_MF_DIR_USERTYPED)output\stl\water.stl   # Source STL File(s)
- SourceDataset_CSV2_5 = $(FME_MF_DIR_USERTYPED)output\offset_values.csv   # Source CSV (Comma Separated Value) File(s)
- SourceDataset_CSV2_4 = $(FME_MF_DIR_USERTYPED)output\offset_values.csv   # Source CSV (Comma Separated Value) File(s)

Readers:
- CSV2_1: CSV2 from $(SourceDataset_CSV2)
- OGCGEOPACKAGE_1: OGCGEOPACKAGE from $(SourceDataset_OGCGEOPACKAGE)
- STL_2: STL from $(SourceDataset_STL)
- CSV2_2: CSV2 from $(SourceDataset_CSV2_5)
- CSV2_3: CSV2 from $(SourceDataset_CSV2_4)

Writers:
- CITYGML_2: CITYGML to $(DestDataset_CITYGML)
- CESIUM3DTILES_1: CESIUM3DTILES to $(DestDataset_CESIUM3DTILES)
- STL_1: STL to $(DestDataset_STL)

CSV (reader CSV2_1)
    attributes: the_geom varchar(50), cartodb_id uint32, id uint32, tree_id uint32, name_ja varchar(33), variant varchar(18), height real32, branch_height uint32, width real32, perimeter uint32, s3_photo varchar(137), photo varchar(80), photo_0_so varchar(23), photo1 varchar(59), photo_1_so varchar(23), photo_miss varchar(107), teiboku_na varchar(72), teiboku_re varchar(37), remarks varchar(103), source varchar(23), _created date, _modified date, _owner uint32, surveyed uint32, flg_lost uint32, carbon uint32, co2 int32, re_survey varchar(27), building varchar(1), citygml_class uint32,
      citygml_function uint32
    -> AttributeManager_2
AttributeManager_2
    ATTR_TABLE = RENAME_SET_VALUE perimeter > diameter (uint32)
    -> AttributeValidator
Note: 以下の値がないレコード, 幹周 (perimeter) 異常値のレコードを除外 / branch_height / height / width / perimeter, (0, 150) を正常値とみなす。 / the_geom
AttributeValidator
    TABLE = branch_height$TYPE$NUM/height$TYPE$NUM/width$TYPE$NUM/diameter$TYPE$NUM/diameter$RANGE$(0,150)/the_geom$TYPE$STRING
    PASSED -> GeometryReplacer
GeometryReplacer
    KIND = wkbhex
    REMOVE_ATTRIBUTE = Yes
    SOURCE = @Value(the_geom)
    KIND_LONG = Hex Encoded OGC Well Known Binary
    -> CsmapReprojector_4
CsmapReprojector_4
    DEST = $(DEST_COORDSYS)
    INTERPOLATION_TYPE_NAME = NearestNeighbor
    RASTER_CELL_SIZE = PreserveCells
    RASTER_TOLERANCE = 0.0
    SOURCE = EPSG:6668
    REPROJECTED -> SpatialFilter [Candidate]
offset_values (reader CSV2_2)
    attributes: x_offset x_coordinate, y_offset y_coordinate, z_offset z_coordinate
    -> FeatureMerger_3 [SUPPLIER]
ground (reader STL_2)
    -> Junction_10
road (reader STL_2)
    -> Junction_10
water (reader STL_2)
    -> Junction_10
Junction_10
    -> FeatureMerger_3 [REQUESTOR]
FeatureMerger_3
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter
Offsetter
    MODE_LOOKUP = CARTESIAN
    XOFF = -@Value(x_offset)
    YOFF = -@Value(y_offset)
    ZOFF = -@Value(z_offset)
    MODE = Cartesian Coordinate
    OFFSET -> CoordinateSystemSetter
CoordinateSystemSetter
    COORDSYS = $(DEST_COORDSYS)
    -> SurfaceDraper [POINTS/LINES]
parsed (reader OGCGEOPACKAGE_1)
    attributes: felt:feature int, felt:has_geometry boolean, felt:h3_index int, felt:geometry_size int, felt:color text, felt:fillOpacity double, felt:id text, felt:locked int, felt:ordering int, felt:showArea int, felt:strokeOpacity int, felt:strokeStyle text, felt:strokeWidth int, felt:type text, gpkg_fid int,PrimaryKey
    -> CsmapReprojector_3
CsmapReprojector_3
    DEST = $(DEST_COORDSYS)
    INTERPOLATION_TYPE_NAME = NearestNeighbor
    RASTER_CELL_SIZE = PreserveCells
    RASTER_TOLERANCE = 0.0
    SOURCE = EPSG:6668
    REPROJECTED -> SpatialFilter [Filter]
Note: 指定の範囲ポリゴン内にあるポイントに限定
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> SurfaceDraper [DRAPE_FEATURES]
SurfaceDraper
    ADDZ = NO
    BREAKLINE_METHOD = Yes
    CONFORMING_TOLERANCE_LOOKUP = AUTO
    DRAPE_TYPE = VERTEX
    INTERPOLATION_TYPE = AUTO
    TOLERANCE = 0
    ADDZ_TYPE = Replace Z
    CONFORMING_TOLERANCE = Automatic
    DRAPED_FEATURES -> CsmapReprojector_5
CsmapReprojector_5
    DEST = EPSG:6668
    INTERPOLATION_TYPE_NAME = NearestNeighbor
    RASTER_CELL_SIZE = PreserveCells
    RASTER_TOLERANCE = 0.0
    SOURCE = $(DEST_COORDSYS)
    REPROJECTED -> Counter
Note: _index: 作業用の仮ID（連番）
Counter
    CNT_ATTR = _index
    SCOPE = Local
    START = 0
    -> JpMeshCodeExtractor
    -> AttributeManager
Note: 3次メッシュコード抽出 / 出力先ファイル名に使用
JpMeshCodeExtractor
    MESHCODE_ATTR = _meshcode
    MESH_TYPE = 3
    -> CoordinateExtractor
CoordinateExtractor
    IND = 0
    RECURSIVE = No
    X_ATTR = _longitude
    Y_ATTR = _latitude
    Z_ATTR = _elevation
    MODE = Specify Coordinate
    -> AttributeManager_geom
    -> DateTimeStamper
DateTimeStamper
    DATETIME_ATTR = _timestamp
    INCLUDE_FRAC_SECONDS = NO
    INCLUDE_OFFSET = NO
    SCOPE = feature
    STAMP_TYPE = datetime
    TIMEZONE = local
    -> AttributeManager_3
AttributeManager_3
    ATTR_TABLE:
      RENAME_SET_VALUE _timestamp > citygml_creationDate (datetime) = @DateTimeFormat(@CurrentAttribute(), %Y-%m-%d)
      SET_TO gml_id (varchar(200)) = veg_@UUID()
      RENAME_SET_VALUE id > gml_name (uint32)
      RENAME_SET_VALUE name_ja > citygml_species (varchar(33))
      RENAME_SET_VALUE height > citygml_height (real32)
      SET_TO citygml_height_units (varchar(1)) = m
      RENAME_SET_VALUE width > citygml_crown_diameter (real32)
      SET_TO citygml_crown_diameter_units (varchar(1)) = m
      SET_TO citygml_trunk_diameter (real64) = @Evaluate(@round(@Value(diameter)*.01,2))
      SET_TO citygml_trunk_diameter_units (varchar(1)) = m
      REMOVE cartodb_id (uint32)
      REMOVE tree_id (uint32)
      REMOVE variant (varchar(18))
      REMOVE branch_height (uint32)
      REMOVE diameter (uint32)
      REMOVE s3_photo (varchar(137))
      REMOVE photo (varchar(80))
      REMOVE photo_0_so (varchar(23))
      REMOVE photo1 (varchar(59))
      REMOVE photo_1_so (varchar(23))
      REMOVE photo_miss (varchar(107))
      REMOVE teiboku_na (varchar(72))
      REMOVE teiboku_re (varchar(37))
      REMOVE remarks (varchar(103))
      REMOVE source (varchar(23))
      REMOVE _created (date)
      REMOVE _modified (date)
      REMOVE _owner (uint32)
      REMOVE surveyed (uint32)
      REMOVE flg_lost (uint32)
      REMOVE carbon (uint32)
      REMOVE co2 (int32)
      REMOVE re_survey (varchar(27))
      REMOVE building (varchar(1))
      SET_TO citygml_class_codeSpace (varchar(200)) = $(CODELISTS)/SolitaryVegetationObject_class.xml
      SET_TO citygml_function{0}.codeSpace (varchar(200)) = $(CODELISTS)/SolitaryVegetationObject_function.xml
      SET_TO citygml_function{0} (varchar(200)) = @Value(citygml_function)
    -> AttributeCreator
AttributeCreator
    ATTR_TABLE:
      SET_TO _geometry_src_desc_lod1{0} (varchar(7)) = 000
      SET_TO _geometry_src_desc_lod1{1} (varchar(7)) = 801
      SET_TO _geometry_src_desc_lod2{0} (uint8) = 000
      SET_TO _geometry_src_desc_lod2{1} (uint16) = 801
      SET_TO _geometry_src_desc_codespace (varchar(200)) = $(CODELISTS)/DataQualityAttribute_geometrySrcDesc.xml
      SET_TO _thematic_src_desc (uint16) = 801
      SET_TO _thematic_src_desc_codespace (varchar(200)) = $(CODELISTS)/DataQualityAttribute_thematicSrcDesc.xml
      SET_TO _lod1_height_type (varchar(5))
      SET_TO _lod1_height_type_codespace (varchar(200)) = $(CODELISTS)/DataQualityAttribute_lod1HeightType.xml
    -> XMLTemplater [ROOT]
XMLTemplater
    OUTPUT_XML_HEADER = Yes
    RESULT_ATTRIBUTE = uro_veg_data_quality_attribute{0}
    ROOT_QUERY_EXPR:
      <uro:DataQualityAttribute xmlns:tran="http://www.opengis.net/citygml/transportation/2.0" xmlns:frn="http://www.opengis.net/citygml/cityfurniture/2.0" xmlns:xlink="http://www.w3.org/1999/xlink" xmlns:tun="http://www.opengis.net/citygml/tunnel/2.0" xmlns:veg="http://www.opengis.net/citygml/vegetation/2.0" xmlns:sch="http://www.ascc.net/xml/schematron" xmlns:gml="http://www.opengis.net/gml" xmlns:dem="http://www.opengis.net/citygml/relief/2.0" xmlns:wtr="http://www.opengis.net/citygml/waterbody/2.0" xmlns:brid="http://www.opengis.net/citygml/bridge/2.0" xmlns:pfx0="urn:oasis:names:tc:ciq:xsdschema:xAL:2.0" xmlns:smil20lang="http://www.w3.org/2001/SMIL20/Language" xmlns:xsi="http://www.w3.org/2001/XMLSchema-instance" xmlns:smil20="http://www.w3.org/2001/SMIL20/" xmlns:bldg="http://www.opengis.net/citygml/building/2.0" xmlns:core="http://www.opengis.net/citygml/2.0" xmlns:grp="http://www.opengis.net/citygml/cityobjectgroup/2.0" xmlns:luse="http://www.opengis.net/citygml/landuse/2.0" xmlns:uro="https://www.geospatial.jp/iur/uro/3.2">
        <uro:geometrySrcDescLod1 codeSpace="{fme:get-attribute("_geometry_src_desc_codespace")}">{fme:get-attribute("_geometry_src_desc_lod1{0}")}</uro:geometrySrcDescLod1>
        <uro:geometrySrcDescLod1 codeSpace="{fme:get-attribute("_geometry_src_desc_codespace")}">{fme:get-attribute("_geometry_src_desc_lod1{1}")}</uro:geometrySrcDescLod1>
        <uro:geometrySrcDescLod2 codeSpace="{fme:get-attribute("_geometry_src_desc_codespace")}">{fme:get-attribute("_geometry_src_desc_lod2{0}")}</uro:geometrySrcDescLod2>
        <uro:geometrySrcDescLod2 codeSpace="{fme:get-attribute("_geometry_src_desc_codespace")}">{fme:get-attribute("_geometry_src_desc_lod2{1}")}</uro:geometrySrcDescLod2>
        <uro:thematicSrcDesc codeSpace="{fme:get-attribute("_thematic_src_desc_codespace")}">{fme:get-attribute("_thematic_src_desc")}</uro:thematicSrcDesc>
        <uro:lod1HeightType codeSpace="{fme:get-attribute("_lod1_height_type_codespace")}">{fme:get-attribute("_lod1_height_type")}</uro:lod1HeightType>
      </uro:DataQualityAttribute>
    VISIBLE_QUERY_VALIDATE = Yes
    -> XMLDeepCleaner
XMLDeepCleaner
    FORMATTING_CHOICE = None
    KEEP_ROOT = Yes
    REMOVE_ALL_COMMENT = Yes
    REMOVE_XML_HEADER = yes
    XML_ATTRIBUTE = @Value(uro_veg_data_quality_attribute{0})
    XML_OUTPUT_ATTR = uro_veg_data_quality_attribute{0}
    -> Junction_4
Note: FeatureMerger : Supplier
Junction_4
    -> Junction_5
Note: AttributeManager_例 : Output
Junction_5
    -> FeatureMerger [SUPPLIER]
AttributeManager_geom
    ATTR_TABLE:
      RENAME_SET_VALUE _longitude > _x (real64)
      RENAME_SET_VALUE _latitude > _y (real64)
      RENAME_SET_VALUE _elevation > _z (real64)
      REMOVE cartodb_id (uint32)
      REMOVE id (uint32)
      REMOVE name_ja (varchar(33))
      REMOVE tree_id (uint32)
      REMOVE variant (varchar(18))
      SET_TO diameter_meter (real64) = @Evaluate(@round(@Value(diameter)*0.01,2))
      REMOVE diameter (uint32)
      REMOVE s3_photo (varchar(137))
      REMOVE photo (varchar(80))
      REMOVE photo_0_so (varchar(23))
      REMOVE photo1 (varchar(59))
      REMOVE photo_1_so (varchar(23))
      REMOVE photo_miss (varchar(107))
      REMOVE teiboku_na (varchar(72))
      REMOVE teiboku_re (varchar(37))
      REMOVE remarks (varchar(103))
      REMOVE source (varchar(23))
      REMOVE _created (date)
      REMOVE _modified (date)
      REMOVE _owner (uint32)
      REMOVE surveyed (uint32)
      REMOVE flg_lost (uint32)
      REMOVE carbon (uint32)
      REMOVE co2 (int32)
      REMOVE re_survey (varchar(27))
      REMOVE building (varchar(1))
      REMOVE citygml_class (uint32)
      REMOVE citygml_function (uint32)
    USER_EXPOSED_ATTRIBUTES = perimeter
    -> CsmapAttributeReprojector
Note: x, y を緯度経度から平面直角座標系の座標値に変換
CsmapAttributeReprojector
    DEST = $(PROJECTION_COORDSYS)
    SOURCE = EPSG:6668
    XATTR = _x
    YATTR = _y
    REPROJECTED -> CoordinateSystemRemover
    REPROJECTED -> AttributeCreator_trunk
    REPROJECTED -> AttributeCreator_crown
Junction
    -> Junction_2
Junction_2
    -> AttributeCreator_lod1
Note: _order = 1
AttributeCreator_trunk
    ATTR_TABLE = SET_TO _order (uint64) = 1
    -> FeatureMerger_trunk [REQUESTOR]
Note: _order = 2
AttributeCreator_crown
    ATTR_TABLE = SET_TO _order (uint64) = 2
    -> FeatureMerger_crown [REQUESTOR]
Note: 3D Tiles用として残す属性
AttributeManager
    ATTR_TABLE:
      REMOVE cartodb_id (uint32)
      REMOVE id (uint32)
      REMOVE tree_id (uint32)
      RENAME_SET_VALUE name_ja > 和名または種名 (varchar(33))
      REMOVE variant (varchar(18))
      RENAME_SET_VALUE height > 樹高（m） (real32)
      RENAME_SET_VALUE branch_height > 枝下高（m） (uint32)
      RENAME_SET_VALUE width > 枝張（m） (real32)
      RENAME_SET_VALUE diameter > 胸高直径(cm) (uint32)
      REMOVE s3_photo (varchar(137))
      REMOVE photo (varchar(80))
      REMOVE photo_0_so (varchar(23))
      REMOVE photo1 (varchar(59))
      REMOVE photo_1_so (varchar(23))
      REMOVE photo_miss (varchar(107))
      REMOVE teiboku_na (varchar(72))
      REMOVE teiboku_re (varchar(37))
      REMOVE remarks (varchar(103))
      REMOVE source (varchar(23))
      REMOVE _created (date)
      REMOVE _modified (date)
      REMOVE _owner (uint32)
      REMOVE surveyed (uint32)
      REMOVE flg_lost (uint32)
      REMOVE carbon (uint32)
      REMOVE co2 (int32)
      REMOVE re_survey (varchar(27))
      REMOVE building (varchar(1))
    USER_EXPOSED_ATTRIBUTES = _band{}.value,_band{}.palette{}.value
    -> Junction_6
Note: FeatureMerger: Supplier (3DTiles)
Junction_6
    -> Junction_3
Junction_3
    -> FeatureMerger_2 [SUPPLIER]
Note: Sort By: _index, order
Sorter_lod2
    SORT_PARM = _index NUMERIC ASCENDING _order NUMERIC ASCENDING
    SORTED -> GeometryPartExtractor
    SORTED -> FeatureMerger_2 [REQUESTOR]
Note: Two CompositeSurfaces -> Individual Faces
GeometryPartExtractor
    GQUERY:
      for $geom in //geometry
      where $geom/@fme_geometry_type = 'IFMEFace'
      return number($geom/@fme_id)
    EXTRACTED -> Aggregator_lod2
Note: Faces -> MultiSurface
Aggregator_lod2
    ACCUM_ATTRS = One
    AGGREGATE_TYPE = Homogeneous Collection (If Possible)
    GROUP_BY = _index
    MODE = Geometry - Assemble One Level
    SEP = ,
    ACCUM_ATTRS_NAME = Use Attributes From One Feature
    AGGREGATE -> AttributeCreator_lod2
Note: -> EPSG:6668
CsmapReprojector
    DEST = EPSG:6668
    INTERPOLATION_TYPE = ,NearestNeighbor
    RASTER_CELL_SIZE_LOOKUP = ,PreserveCells
    RASTER_TOLERANCE = 0.0
    SOURCE = $(PROJECTION_COORDSYS)
    INTERPOLATION_TYPE_NAME = Nearest Neighbor
    RASTER_CELL_SIZE = Preserve Cells
    REPROJECTED -> FeatureMerger [REQUESTOR]
Note: 主題属性をジオメトリに結合 / Join On: / Requestor / Supplier / Comparison Mode / @Value(_index) / @Value(_index) / Automatic / Merge Parameters: / Feature Merge Type: Attributes Only / Process Duplicate Suppliers <checked>
FeatureMerger
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(_index) @Value(_index) AUTO
    MERGE_TYPE_VAL = ATTRIBUTES
    PROCESS_DUPS = YES
    REJECT_NULL_MISSING_KEYS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> SolitaryVegetationObject (writer CITYGML_2)
SolitaryVegetationObject (writer CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), uro_point_cloud{}.xlink_href xml_buffer, uro_veg_data_quality_attribute{} xml_xml, uro_veg_dm_attribute{} xml_xml, uro_veg_facility_attribute{} xml_xml, uro_veg_facility_id_attribute{} xml_xml, uro_veg_facility_type_attribute{} xml_xml, uro_veg_key_value_pair_attribute{} xml_xml, citygml_class xml_buffer, citygml_class_codeSpace xml_buffer, citygml_function{} xml_buffer, citygml_function{}.codeSpace xml_buffer, citygml_usage{} xml_buffer, citygml_usage{}.codeSpace xml_buffer, citygml_species xml_buffer, citygml_species_codeSpace xml_buffer, citygml_height xml_real64,
      citygml_height_units xml_buffer, citygml_trunk_diameter xml_real64, citygml_trunk_diameter_units xml_buffer, citygml_crown_diameter xml_real64, citygml_crown_diameter_units xml_buffer, citygml_level_of_detail{} xml_buffer
FeatureMerger_2
    ATTR_ACCUM_MODE = Merge Supplier
    ATTR_CONFLICT_RES_LOOKUP = REQUESTOR_IF_CONFLICT
    IGNORE_NULLS = No
    JOIN_KEYS = @Value(_index) @Value(_index) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PROJReprojector
    MERGED -> Junction_8
Junction_8
    -> FeatureMerger_4 [REQUESTOR]
offset_values (reader CSV2_3)
    attributes: x_offset x_coordinate, y_offset y_coordinate, z_offset z_coordinate
    -> FeatureMerger_4 [SUPPLIER]
FeatureMerger_4
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter_2
Offsetter_2
    MODE_LOOKUP = CARTESIAN
    XOFF = @Value(x_offset)
    YOFF = @Value(y_offset)
    ZOFF = @Value(z_offset)
    MODE = Cartesian Coordinate
    OFFSET -> Junction_9
Junction_9
    -> jyumoku (writer STL_1)
Note: jyumoku: stl [STL]
jyumoku (writer STL_1)

Bookmark: LOD1ジオメトリ（樹木全体をカバーする立体）作成
CoordinateSystemRemover
    -> VertexCreator
VertexCreator
    MEASURE_TYPE_LOOKUP = CONTINUOUS
    MODE = REPLACE
    REMOVE_ATTRIBUTES = No
    XVAL = @Value(_x)
    YVAL = @Value(_y)
    MEASURE_TYPE = Continuous
    MODE_NAME = Replace with Point
    -> Bufferer_lod1
Bufferer_lod1
    ANGLE = 22.5
    CAP_STYLE_LOOKUP = CAP_ARC
    CORNER_STYLE_LOOKUP = JOIN_ARC
    MODE = AREA
    OFFSET = @Value(width)*0.5
    OFFSET_UNITS = NONE
    PRECISION = APPROX
    CAP_STYLE = Arc
    CORNER_STYLE = Arc
    BUFFERED -> ArcStroker_lod1
ArcStroker_lod1
    MAKE_POLY = No
    NUM = 32
    STROKE_MODE = NUM_EDGES
    STROKE_CHOICE = Number of Interpolated Edges
    STROKED -> 3DForcer_lod1
3DForcer_lod1
    KEEPZVAL = No
    ZVALATTR = @Value(_z)
    -> Extruder_lod1
Extruder_lod1
    DIRECTION_LOOKUP = VERTICAL
    DISTANCE = @Value(height)
    DIRECTION = Vertical
    EXTRUDED -> Junction

Bookmark: citygml_lod_name プロパティ設定
Note: citygmll_lod_name = lod1Geometry
AttributeCreator_lod1
    ATTR_TABLE = SET_TO citygml_lod_name (buffer) = lod1Geometry
    -> GeometryPropertySetter
Note: citygmll_lod_name = lod2Geometry
AttributeCreator_lod2
    ATTR_TABLE = SET_TO citygml_lod_name (buffer) = lod2Geometry
    -> GeometryPropertySetter
GeometryPropertySetter
    DO_REMOVE_ATTR = *
    OVERWRITE_CHOICE_OPT = yes
    SETTYPE_PARAM = Traits From Attributes
    SRC_ATTRS = citygml_lod_name
    OVERWRITE_CHOICE = Yes
    REMOVE_ATTRIBUTE = Yes
    SET -> Sorter

Bookmark: 樹形3Dオブジェクトのパーツ（単位サイズの樹幹、樹冠）作成
Creator
    GEOM = <?xml version="1.0" encoding="US_ASCII" standalone="no" ?><geometry><point><coord x="0" y="0" z="0"/></point></geometry>
    GEOMTYPE = Geometry Object
    NUM = 1
    CREATED -> Bufferer_t
    CREATED -> Bufferer_c
Bufferer_t
    ANGLE = 22.5
    CAP_STYLE_LOOKUP = CAP_ARC
    CORNER_STYLE_LOOKUP = JOIN_ARC
    MODE = AREA
    OFFSET = 0.5
    OFFSET_UNITS = NONE
    PRECISION = APPROX
    CAP_STYLE = Arc
    CORNER_STYLE = Arc
    BUFFERED -> ArcStroker_t
ArcStroker_t
    MAKE_POLY = No
    NUM = 16
    STROKE_MODE = NUM_EDGES
    STROKE_CHOICE = Number of Interpolated Edges
    STROKED -> Extruder_t
Extruder_t
    DIRECTION_LOOKUP = VERTICAL
    DISTANCE = 1
    DIRECTION = Vertical
    EXTRUDED -> Clipper [CLIPPER]
    EXTRUDED -> GeometryCoercer_trunk
Note: Etrusion -> CompositeSurface
GeometryCoercer_trunk
    GQUERY:
      for $geom in //geometry
      where $geom/count(parent::geometry) = 0
      return number($geom/@fme_id)
    KIND = fme_composite_surface
    COERCED -> FeatureMerger_trunk [SUPPLIER]
Bufferer_c
    MODE = SOLID
    OFFSET = 0.5
    SPHERE_DIVISIONS = 3
    BUFFERED -> Scaler_c
Note: Z Scale = 1.5
Scaler_c
    DISABLE_FACTORIES = __DISABLED__
    RASTER_SCALING = Extents
    TEXT_LOC_ONLY = Location and Size
    XSCALE = 1
    YSCALE = 1
    ZSCALE = 1.5
    SCALE_ORIGIN = 0,0
    SCALED -> Offsetter_c
Note: Z Offset: 0.25
Offsetter_c
    MODE_LOOKUP = CARTESIAN
    XOFF = 0
    YOFF = 0
    ZOFF = 0.25
    MODE = Cartesian Coordinate
    OFFSET -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> GeometryCoercer_crown
Note: BRepSolid -> CompositeSurface
GeometryCoercer_crown
    GQUERY:
      for $geom in //geometry
      where $geom/count(parent::geometry) = 0
      return number($geom/@fme_id)
    KIND = fme_composite_surface
    COERCED -> FeatureMerger_crown [SUPPLIER]

Bookmark: 樹幹ジオメトリの結合、サイズ調整、移動
FeatureMerger_trunk
    JOIN_KEYS = 1 1 AUTO
    MERGE_TYPE_VAL = GEOM_BUILD
    PRESERVE_FEATURE_ORDER_LOOKUP = PER_OUTPUT_PORT
    PROCESS_DUPS = NO
    REJECT_NULL_MISSING_KEYS = No
    SUPPLIERS_FIRST = No
    MERGE_TYPE = Geometry
    MERGED -> Scaler_trunk
Scaler_trunk
    DISABLE_FACTORIES = __DISABLED__
    RASTER_SCALING = Extents
    TEXT_LOC_ONLY = Location and Size
    XSCALE = @Value(diameter_meter)
    YSCALE = @Value(diameter_meter)
    ZSCALE = @Value(branch_height)
    SCALE_ORIGIN = 0,0
    SCALED -> Offsetter_trunk
Offsetter_trunk
    MODE_LOOKUP = CARTESIAN
    XOFF = @Value(_x)
    YOFF = @Value(_y)
    ZOFF = @Value(_z)
    MODE = Cartesian Coordinate
    OFFSET -> Sorter_lod2

Bookmark: 樹冠ジオメトリの結合、サイズ調整、移動
FeatureMerger_crown
    JOIN_KEYS = 1 1 AUTO
    MERGE_TYPE_VAL = GEOM_BUILD
    PRESERVE_FEATURE_ORDER_LOOKUP = PER_OUTPUT_PORT
    PROCESS_DUPS = NO
    REJECT_NULL_MISSING_KEYS = No
    SUPPLIERS_FIRST = No
    MERGE_TYPE = Geometry
    MERGED -> Scaler_crown
Scaler_crown
    DISABLE_FACTORIES = __DISABLED__
    RASTER_SCALING = Extents
    TEXT_LOC_ONLY = Location and Size
    XSCALE = @Value(width)
    YSCALE = @Value(width)
    ZSCALE = @Value(height)-@Value(branch_height)
    SCALE_ORIGIN = 0,0
    SCALED -> Offsetter_crown
Offsetter_crown
    MODE_LOOKUP = CARTESIAN
    XOFF = @Value(_x)
    YOFF = @Value(_y)
    ZOFF = @Value(_z)+@Value(branch_height)
    MODE = Cartesian Coordinate
    OFFSET -> Sorter_lod2

Bookmark: LOD1,LOD2 を集約して MultipleGeometry に変換
Note: Sort By: _index
Sorter
    SORT_PARM = _meshcode NUMERIC ASCENDING _index NUMERIC ASCENDING
    SORTED -> Aggregator
Aggregator
    ACCUM_ATTRS = One
    AGGREGATE_TYPE = Homogeneous Collection (If Possible)
    GROUP_BY = _index _meshcode
    MODE = Geometry - Assemble One Level
    SEP = ,
    ACCUM_ATTRS_NAME = Use Attributes From One Feature
    AGGREGATE -> MultipleGeometrySetter
Note: 省略可
MultipleGeometrySetter
    CONTAIN_INDIVID_GEOMS = Yes
    -> CsmapReprojector

Bookmark: 3D Tilesに変換
Note: EPSG:6677 -> 4326
PROJReprojector
    DEST = EPSG:4326
    INTERPOLATION_TYPE = ,NearestNeighbor
    RASTER_CELL_SIZE_LOOKUP = ,PreserveCells
    RASTER_TOLERANCE = 0.0
    SOURCE = EPSG:6677
    TRANSFORM_TYPE = Automatic Transformation
    INTERPOLATION_TYPE_NAME = Nearest Neighbor
    RASTER_CELL_SIZE = Preserve Cells
    REPROJECTED -> CsmapReprojector_2
Note: 楕円体高に変換
CsmapReprojector_2
    DEST = EPSG:4326
    GEOID_HEIGHT_GRID = $(FME_MF_DIR_USERTYPED)\resources\gsigeo2011\gsigeo2011_ver2_2.gdc
    INTERPOLATION_TYPE = ,NearestNeighbor
    RASTER_CELL_SIZE_LOOKUP = ,PreserveCells
    RASTER_TOLERANCE = 0.0
    SOURCE = EPSG:4326
    VERTICAL_HANDLING_LOOKUP = 3D_ORTHOMETRIC_TO_ELLIPSOID
    INTERPOLATION_TYPE_NAME = Nearest Neighbor
    RASTER_CELL_SIZE = Preserve Cells
    VERTICAL_HANDLING = Orthometric height -> Geocentric or ellipsoid height
    REPROJECTED -> GeometryColorSetter
Note: color = 255,255,255,255
GeometryColorSetter
    ALGORITHM = MANUAL
    ALPHA = 1
    DEFINITION = DEFINITION_BOTH
    FILL_COLOR = 1,1,1
    RECURSIVE = YES
    MODE = Fixed
    REC = Yes
    SIDE = Both
    COLORED -> AttributeKeeper
AttributeKeeper
    CREATE_BULK_MODE_FEATURES = NO
    KEEP_ATTRS = 和名または種名,枝下高（m）,枝張（m）,樹高（m）,胸高直径(cm)
    -> jyumoku (writer CESIUM3DTILES_1)
jyumoku (writer CESIUM3DTILES_1)
    attributes: 和名または種名 string, 樹高（m） float, 枝下高（m） int, 枝張（m） float, 胸高直径(cm) int

FME custom transformer JpMeshCodeExtractor
Extracts Japanese Standard Mesh Code of the mesh containing the first coordinate of the input feature. 
    If the input feature doesn't have coordinates, it will be output from the <Rejected> port. 
    Notes:
    This transformer is valid only for a geographic data on Japanese area with LL coordinate system.
    This transformer rounds the coordinate values into milliseconds when computing mesh code. So an computational error may not be avoided if the coordinate is very close to a mesh boundary.
    This transformer supports these Japanese standard mesh types.
    Primary Standard Mesh - spacing (W x H): 3600sec. x 2400sec., mesh code format: "AABB"
    Secondary Standard Mesh - spacing (W x H): 450sec. x 300sec., mesh code format: "AABB-CD"
    Tertiary Standard Mesh - spacing (W x H): 45sec. x 30sec., mesh code format: "AABB-CD-EF"
    1/2 Subdivided Mesh - spacing (W x H): 22.5sec. x 15sec., mesh code format: "AABB-CD-EF-G"
    1/4 Subdivided Mesh - spacing (W x H): 11.25sec. x 7.5sec., mesh code format: "AABB-CD-EF-G-H" 
    1/8 Subdivided Mesh - spacing (W x H): 5.625sec. x 3.75sec., mesh code format: "AABB-CD-EF-G-H-I"
    1/10 Subdivided Mesh - spacing (W x H): 4.5sec. x 3sec., mesh code format: "AABB-CD-EF-XY
    A - I, X and Y in the formats represents a digit determined by the followings.
    AA = south end latitude (degrees) of the primary mesh * 1.5
    BB = west end longitude (degrees) of the primary mesh - 100
    C = row index in the parent primary mesh (0:south - 7:north end)
    D = column index in the parent primary mesh (0:west - 7:east end)
    E = row index in the parent secondary mesh (0:south - 9:north end)
    F = column index in the parent secondary mesh (0:west - 9:east end)
    G = 1:left-bottom, 2:right-bottom, 3:left-top, 4:right-top in the parent tertiary mesh
    H = 
    1:left-bottom, 2:right-bottom, 3:left-top, 4:right-top in the parent 1/2 subdivided mesh
    I = 
    1:left-bottom, 2:right-bottom, 3:left-top, 4:right-top in the parent 1/4 subdivided mesh
    X = row index in the parent tertiary mesh (0:south - 9:north end)
    Y = column index in the parent tertiary mesh (0:west - 9:east end)
Parameters
    Mesh Type:
    Choose the mesh type.
    -----
    Primary Standard Mesh
    Secondary Standard Mesh
    Tertiary Standard Mesh
    1/2 Subdivided Mesh
    1/4 Subdivided Mesh
    1/8 Subdivided Mesh
    1/10 Subdivided Mesh
    -----
    Mesh Code Attribute:
    Specify an attribute name which will store the mesh code.
    Delimiter String:
    Specify a delimiter string which should be used as delimiters in the mesh code.
    You can leave this parameter blank if you don't need to delimit the mesh code.

Parameters:
- MESH_TYPE = 3
- MESHCODE_ATTR = _meshcode   # TYPE:varchar(200) Mesh Code Attribute
- DELIMITER = -   # Delimiter String

Input (input)
    -> Tester
Tester
    BOOL_OP = OR
    TEST_CLAUSE = TEST 0 < @Evaluate(@NumCoords())
    TEST_MODE = Automatic
    PASSED -> ParameterFetcher
    FAILED -> <Rejected> (output)
ParameterFetcher
    ATTR_LIST = jpmeshcodeextractor.meshtype {$(MESH_TYPE)} jpmeshcodeextractor.delimiter {$(DELIMITER)}
    -> CoordinateExtractor
CoordinateExtractor
    IND = 0
    X_ATTR = jpmeshcodeextractor.x
    Y_ATTR = jpmeshcodeextractor.y
    Z_DEFAULT = -9999
    -> PythonCaller
PythonCaller
    NEW_ATTRIBUTES = jpmeshcodeextractor.meshcode
    PYTHONSOURCE:
      import fmeobjects

      # 2015-11-30: Improved to avoid unexpected mesh code from an aggregate geometry.
      # 2015-05-28: Added 1/10 subdivided mesh code creation support.

      def extractMeshCode(feature):
          mtype = int(feature.getAttribute('jpmeshcodeextractor.meshtype'))
          delim = feature.getAttribute('jpmeshcodeextractor.delimiter')
          meshAttr = 'jpmeshcodeextractor.meshcode'

          # Get latitude and longitude of the first coordinate of the feature, in milliseconds.
          # 2015-11-30: Replaced FMEFeature.getCoordinate method with the CoordinateExtractor
          # to avoid unexpected coordinate values from an aggregate geometry.
          #coord = feature.getCoordinate(0)
          coord = (float(feature.getAttribute('jpmeshcodeextractor.x')),
              float(feature.getAttribute('jpmeshcodeextractor.y')))
          lat_ms = int(round(coord[1] * 3600000.0))
          lon_ms = int(round(coord[0] * 3600000.0))

          # Primary Mesh Code
          a, b = lat_ms // 2400000, int(coord[0]) - 100
          meshCode = '%02d%02d' % (a, b)
          if mtype == 1:
              feature.setAttribute(meshAttr, meshCode)
              return
          lat_ms -= a * 2400000
          lon_ms -= (b + 100) * 3600000

          # Secondary Mesh Code
          c, d = lat_ms // 300000, lon_ms // 450000
          meshCode = '%s%s%d%d' % (meshCode, delim, c, d)
          if mtype == 2:
              feature.setAttribute(meshAttr, meshCode)
              return
          lat_ms %= 300000
          lon_ms %= 450000

          # Tertiary Mesh Code
          e, f = lat_ms // 30000, lon_ms // 45000
          meshCode = '%s%s%d%d' % (meshCode, delim, e, f)
          if mtype == 3:
              feature.setAttribute(meshAttr, meshCode)
              return
          lat_ms %= 30000
          lon_ms %= 45000

          if mtype == 10:
              # 1/10 Subdivided Mesh Code
              x, y = lat_ms // 3000, lon_ms // 4500
              meshCode = '%s%s%d%d' % (meshCode, delim, x, y)
              feature.setAttribute(meshAttr, meshCode)
          else:
              # 1/2 Subdivided Mesh Code
              div = (1 if lon_ms < 22500 else 2) + (0 if lat_ms < 15000 else 2)
              meshCode = '%s%s%d' % (meshCode, delim, div)
              if mtype == 4:
                  feature.setAttribute(meshAttr, meshCode)
                  return
              lat_ms %= 15000
              lon_ms %= 22500

              # 1/4 Subdivided Mesh Code
              div = (1 if lon_ms < 11250 else 2) + (0 if lat_ms < 7500 else 2)
              meshCode = '%s%s%d' % (meshCode, delim, div)
              if mtype == 5:
                  feature.setAttribute(meshAttr, meshCode)
                  return
              lat_ms %= 7500
              lon_ms %= 11250

              # 1/8 Subdivided Mesh Code
              div = (1 if lon_ms < 5625 else 2) + (0 if lat_ms < 3750 else 2)
              meshCode = '%s%s%d' % (meshCode, delim, div)
              feature.setAttribute(meshAttr, meshCode)
    PYTHONSYMBOL = extractMeshCode
    -> BulkAttributeRenamer
BulkAttributeRenamer
    ATTRCHOICE_ACTION = SELECTED
    ATTRLIST = jpmeshcodeextractor.meshcode
    PATTERN_ACTION = REGEXPREPLACE
    REPLACE_PATTERN = .*
    REPLACE_STR = $(MESHCODE_ATTR)
    ATTRCHOICE = Selected Attributes
    PATTERN_ACTION_DISP = Regular Expression Replace
    -> BulkAttributeRemover
BulkAttributeRemover
    ATTR_EXP = jpmeshcodeextractor.
    -> Output (output)
Output (output)
<Rejected> (output)

FME custom transformer XMLDeepCleaner
Removes all empty elements from an XML text specified through the XML Attribute parameter.  
A similar function is provided by XMLFormatter (set "Yes" to the "Remove Empty Elements" parameter), but this transformer ignores XML attributes and comments to determine if an XML element is empty, so the result may be different from XMLFormatter.
Example
Source XML Text
<root>
    <a>
        <b></b>
        <!-- empty but has a comment -->
    </a>
    <a>
        <b>value</b>
        <!-- has a value -->
    </a>
    <a attr="1">
        <b></b>
        <!-- empty but parent has an attribute -->
    </a>
    <a>
        <b attr="2"></b>
        <!-- empty but has an attribute -->
    </a>
</root>
XMLFormatter (Remove Empty Elements : Yes)
<root>
    <a>
        <!-- empty but has a comment -->
    </a>
    <a>
        <b>value</b>
        <!-- has a value -->
    </a>
    <a attr="1">
        <!-- empty but parent has an attribute -->
    </a>
    <a>
        <b attr="2"/>
        <!-- empty but has an attribute -->
    </a>
</root>
XMLDeepCleaner
<root>
    <a>
        <b>value</b>
        <!-- has a value -->
    </a>
</root>

Parameters:
- XML_ATTRIBUTE =   # XML Attribute
- KEEP_ROOT = Yes   # Keep Root Element,Yes%Make Result Missing,No If All Elements are Empty
- FORMATTING_CHOICE = None   # XML"%"Linearize XML" Formatting Type
- REMOVE_ALL_COMMENT = Yes   # Remove All Comments
- REMOVE_XML_HEADER = no   # Remove XML Header
- XML_OUTPUT_ATTR =   # Attribute to contain XML output

Input (input)
    -> Counter
Counter
    CNT_ATTR = __index
    SCOPE = Local
    START = 0
    -> Tester_2
    -> AttributeKeeper
Tester_2
    BOOL_OP = OR
    TEST_CLAUSE = TEST $(KEEP_ROOT) = Yes
    TEST_MODE = TEST
    PASSED -> XMLUpdater [DOCUMENT]
    FAILED -> XMLUpdater_2 [DOCUMENT]
AttributeKeeper
    CREATE_BULK_MODE_FEATURES = NO
    KEEP_ATTRS = __index
    -> XMLUpdater [UPDATE]
    -> XMLUpdater_2 [UPDATE]
XMLUpdater
    GROUP_BY = __index
    OUTPUT_XML_HEADER_LOOKUP = NO
    QUERY_VALIDATE = YES
    RESULT_ATTRIBUTE = __attribute
    UPDATE_TABLE = GENERATE_QUERY DELETE for $x in /*//* where not(normalize-space(data($x))) return $x <Unused> <Unused>
    XML_TEXT = $(XML_ATTRIBUTE)
    XML_TYPE = Text or Attribute
    OUTPUT_XML_HEADER = No
    VISIBLE_QUERY_VALIDATE = Yes
    DOCUMENT -> AttributeRemover
XMLUpdater_2
    GROUP_BY = __index
    OUTPUT_XML_HEADER_LOOKUP = NO
    QUERY_VALIDATE = YES
    RESULT_ATTRIBUTE = __attribute
    UPDATE_TABLE = GENERATE_QUERY DELETE for $x in //* where not(normalize-space(data($x))) return $x <Unused> <Unused>
    XML_TEXT = $(XML_ATTRIBUTE)
    XML_TYPE = Text or Attribute
    OUTPUT_XML_HEADER = No
    VISIBLE_QUERY_VALIDATE = Yes
    DOCUMENT -> AttributeRemover
AttributeRemover
    REMOVE_ATTRS = __index
    -> Tester
Tester
    BOOL_OP = OR
    TEST_CLAUSE = TEST __attribute NOT_ATTRIBUTE_HAS_A_VALUE ""
    TEST_MODE = TEST
    PASSED -> AttributeRemover_2
    FAILED -> XMLFormatter
XMLFormatter
    COLLAPSE_EMPTY_ELEMENT = No
    FORMAT_MODE = $(FORMATTING_CHOICE)
    INDENT_SIZE = 1
    LIST_NAME = _xml_error
    MOVE_NAMESPACE_TO_ROOT = No
    NAMESPACE_CLEANUP = Yes
    OUTPUT_ENCODING = utf-8
    PARSER_CHOICE = Xerces
    REMOVE_ALL_COMMENT = $(REMOVE_ALL_COMMENT)
    REMOVE_DTD = No
    REMOVE_EMPTY_ELEMENT = No
    REMOVE_XML_HEADER = $(REMOVE_XML_HEADER)
    REPLACE_TABS_WITH_SPACES = no
    SCHEMALOC_CLEANUP = No
    TEXT_INDENT = no
    WHITESPACE_HANDLING = Remove excess whitespace
    XML_ATTR_TEXT = __attribute
    XML_INPUT_TYPE = Attribute Specifying XML Text
    XML_OUTPUT_ATTR = $(XML_OUTPUT_ATTR)
    XML_OUTPUT_TYPE = Attribute
    FORMATTING_CHOICE = $(FORMATTING_CHOICE)
    PASSED -> AttributeRemover_2
    FAILED -> AttributeRemover_3
AttributeRemover_2
    REMOVE_ATTRS = __attribute
    -> Output (output)
Output (output)
AttributeRemover_3
    REMOVE_ATTRS = __attribute
    -> <Rejected> (output)
<Rejected> (output)
