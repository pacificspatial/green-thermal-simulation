FME workspace s1_地形モデル変換_citygmlをstl変換.fmw
History: 2026-01-07,Takashi Iijima,オフセット量算出式を3項演算子による条件式に変更 (AttributeManager)

Parameters:
- SourceDataset_OGCGEOPACKAGE = $(FME_MF_DIR_USERTYPED)source\シミュレーション範囲 Dissolved.gpkg   # Simulation Extents [GeoPackage]
- SourceDataset_CITYGML_3 = $(FME_MF_DIR_USERTYPED)source\13101_chiyoda-ku_pref_2023_citygml_2_op\udx\luse\533946_luse_6697_op.gml   # Source CityGML File(s) [luse]
- SourceDataset_CITYGML = $(FME_MF_DIR_USERTYPED)source\13101_chiyoda-ku_pref_2023_citygml_2_op\udx\dem\533946_dem_6697_op.gml   # Source CityGML File(s) [dem]
- SourceDataset_JP_FGD_DEM2 = ""$(FME_MF_DIR_USERTYPED)source\fg_dem5a\FG-GML-5339-46-21-DEM5A-20250822.xml" "$(FME_MF_DIR_USERTYPED)source\fg_dem5a\FG-GML-5339-46-20-DEM5A-20250822.xml""   # Source FGD DEM XML File(s)
- DEST_COORDSYS = EPSG:6677
- DestDataset_STL = $(FME_MF_DIR_USERTYPED)output   # Destination Root Folder

Readers:
- OGCGEOPACKAGE_1: OGCGEOPACKAGE from $(SourceDataset_OGCGEOPACKAGE)
- CITYGML_2: CITYGML from $(SourceDataset_CITYGML_3)
- CITYGML_1: CITYGML from $(SourceDataset_CITYGML)
- JP_FGD_DEM2_1: JP_FGD_DEM2 from $(SourceDataset_JP_FGD_DEM2)

Writers:
- STL_1: STL to $(DestDataset_STL)
- CSV2_1: CSV2 to $(DestDataset_STL)

Tester
    BOOL_OP = OR
    TEST_CLAUSE = TEST @Value(gml_name) IN 53394620,53394621
    TEST_MODE = TEST
    PASSED -> CsmapReprojector_2
CsmapReprojector_2
    DEST = $(DEST_COORDSYS)
    INTERPOLATION_TYPE_NAME = NearestNeighbor
    RASTER_CELL_SIZE = PreserveCells
    RASTER_TOLERANCE = 0.0
    REPROJECTED -> Junction_3
    REPROJECTED -> Clipper [CLIPPER]
Junction_3
    -> Junction_2
Junction_2
    -> TINGenerator [POINTS/LINES]
Note: 基盤地図情報5mメッシュDEM / [JP_FGD_DEM2]
DEMRASTER (reader JP_FGD_DEM2_1)
    attributes: fid char(50), devDate date, lfSpanFr date, lfSpanTo date, orgGILvl char(50), orgMDId char(50), mesh char(10), type char(50), fgd_dem_type char(10), srsName char(20)
    -> CsmapReprojector_3
CsmapReprojector_3
    DEST = $(DEST_COORDSYS)
    INTERPOLATION_TYPE_NAME = NearestNeighbor
    RASTER_CELL_SIZE = PreserveCells
    RASTER_TOLERANCE = 0.0
    REPROJECTED -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> TINGenerator [POINTS/LINES]
Note: PLATEAU 地形モデルが作成されていない範囲を基盤地図情報5mメッシュDEMで補完して単一のTINを作成
TINGenerator
    BREAKLINE_METHOD = Yes
    CONFORMING_TOLERANCE_LOOKUP = AUTO
    TOLERANCE = 0.1
    CONFORMING_TOLERANCE = Automatic
    TRIANGLES -> Clipper_2 [CANDIDATE]
2DForcer
    2D -> CsmapReprojector_4
CsmapReprojector_4
    DEST = $(DEST_COORDSYS)
    INTERPOLATION_TYPE_NAME = NearestNeighbor
    RASTER_CELL_SIZE = PreserveCells
    RASTER_TOLERANCE = 0.0
    REPROJECTED -> AttributeFilter
Note: class=204: 水面 / class=215: 道路用地
AttributeFilter
    ATTR_NAME = citygml_class
    ATTR_VALUES = 204,215,<Empty>,<Missing>,<Null>,<Unfiltered>
    204 -> AttributeManager_Water
    215 -> AttributeManager_Road
Note: _landuse = water
AttributeManager_Water
    ATTR_TABLE:
      SET_TO _landuse (varchar(5)) = water
      REMOVE gml_id (buffer)
      REMOVE gml_parent_id (buffer)
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (xml)
      REMOVE externalReference{}.externalObject.uri (xml)
      REMOVE externalReference{}.informationSystem (xml)
      REMOVE citygml_generalizes_to{}.xlink_href (buffer)
      REMOVE citygml_relative_to_terrain (varchar(33))
      REMOVE citygml_relative_to_water (varchar(38))
      REMOVE citygml_appearance{}.xlink_href (buffer)
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_level_of_detail{} (buffer)
      REMOVE uro_ifc_land_use_attribute{} (xml)
      REMOVE uro_land_use_detail_attribute{}.uro_land_use_detail_attribute_uro_id (buffer)
      REMOVE uro_land_use_detail_attribute{}.uro_land_use_detail_attribute_uro_org_land_use (buffer)
      REMOVE uro_land_use_detail_attribute{}.uro_land_use_detail_attribute_uro_org_land_use_codeSpace (buffer)
      REMOVE uro_land_use_detail_attribute{}.uro_land_use_detail_attribute_uro_nominal_area (real64)
      REMOVE uro_land_use_detail_attribute{}.uro_land_use_detail_attribute_uro_nominal_area_units (buffer)
      REMOVE uro_land_use_detail_attribute{}.uro_land_use_detail_attribute_uro_owner_type (buffer)
      REMOVE uro_land_use_detail_attribute{}.uro_land_use_detail_attribute_uro_owner_type_codeSpace (buffer)
      REMOVE uro_land_use_detail_attribute{}.uro_land_use_detail_attribute_uro_owner (buffer)
      REMOVE uro_land_use_detail_attribute{}.uro_land_use_detail_attribute_uro_area_in_square_meter (real64)
      REMOVE uro_land_use_detail_attribute{}.uro_land_use_detail_attribute_uro_area_in_square_meter_units (buffer)
      REMOVE uro_land_use_detail_attribute{}.uro_land_use_detail_attribute_uro_area_in_ha (real64)
      REMOVE uro_land_use_detail_attribute{}.uro_land_use_detail_attribute_uro_area_in_ha_units (buffer)
      REMOVE uro_land_use_detail_attribute{}.uro_land_use_detail_attribute_uro_building_coverage_rate (real64)
      REMOVE uro_land_use_detail_attribute{}.uro_land_use_detail_attribute_uro_floor_area_rate (real64)
      REMOVE uro_land_use_detail_attribute{}.uro_land_use_detail_attribute_uro_specified_building_coverage_rate (real64)
      REMOVE uro_land_use_detail_attribute{}.uro_land_use_detail_attribute_uro_specified_floor_area_rate (real64)
      REMOVE uro_land_use_detail_attribute{}.uro_land_use_detail_attribute_uro_standard_floor_area_rate (real64)
      REMOVE uro_land_use_detail_attribute{}.uro_land_use_detail_attribute_uro_urban_plan_type (buffer)
      REMOVE uro_land_use_detail_attribute{}.uro_land_use_detail_attribute_uro_urban_plan_type_codeSpace (buffer)
      REMOVE uro_land_use_detail_attribute{}.uro_land_use_detail_attribute_uro_area_classification_type (buffer)
      REMOVE uro_land_use_detail_attribute{}.uro_land_use_detail_attribute_uro_area_classification_type_codeSpace (buffer)
      REMOVE uro_land_use_detail_attribute{}.uro_land_use_detail_attribute_uro_districts_and_zones_type{} (buffer)
      REMOVE uro_land_use_detail_attribute{}.uro_land_use_detail_attribute_uro_districts_and_zones_type{}.codeSpace (buffer)
      REMOVE uro_land_use_detail_attribute{}.uro_land_use_detail_attribute_uro_prefecture (buffer)
      REMOVE uro_land_use_detail_attribute{}.uro_land_use_detail_attribute_uro_prefecture_codeSpace (buffer)
      REMOVE uro_land_use_detail_attribute{}.uro_land_use_detail_attribute_uro_city (buffer)
      REMOVE uro_land_use_detail_attribute{}.uro_land_use_detail_attribute_uro_city_codeSpace (buffer)
      REMOVE uro_land_use_detail_attribute{}.uro_land_use_detail_attribute_uro_reference (buffer)
      REMOVE uro_land_use_detail_attribute{}.uro_land_use_detail_attribute_uro_note (buffer)
      REMOVE uro_land_use_detail_attribute{}.uro_land_use_detail_attribute_uro_survey_year (buffer)
      REMOVE uro_luse_data_quality_attribute{}.uro_data_quality_attribute_uro_geometry_src_desc_lod0{} (buffer)
      REMOVE uro_luse_data_quality_attribute{}.uro_data_quality_attribute_uro_geometry_src_desc_lod0{}.codeSpace (buffer)
      REMOVE uro_luse_data_quality_attribute{}.uro_data_quality_attribute_uro_geometry_src_desc_lod1{} (buffer)
      REMOVE uro_luse_data_quality_attribute{}.uro_data_quality_attribute_uro_geometry_src_desc_lod1{}.codeSpace (buffer)
      REMOVE uro_luse_data_quality_attribute{}.uro_data_quality_attribute_uro_geometry_src_desc_lod2{} (buffer)
      REMOVE uro_luse_data_quality_attribute{}.uro_data_quality_attribute_uro_geometry_src_desc_lod2{}.codeSpace (buffer)
      REMOVE uro_luse_data_quality_attribute{}.uro_data_quality_attribute_uro_geometry_src_desc_lod3{} (buffer)
      REMOVE uro_luse_data_quality_attribute{}.uro_data_quality_attribute_uro_geometry_src_desc_lod3{}.codeSpace (buffer)
      REMOVE uro_luse_data_quality_attribute{}.uro_data_quality_attribute_uro_geometry_src_desc_lod4{} (buffer)
      REMOVE uro_luse_data_quality_attribute{}.uro_data_quality_attribute_uro_geometry_src_desc_lod4{}.codeSpace (buffer)
      REMOVE uro_luse_data_quality_attribute{}.uro_data_quality_attribute_uro_thematic_src_desc{} (buffer)
      REMOVE uro_luse_data_quality_attribute{}.uro_data_quality_attribute_uro_thematic_src_desc{}.codeSpace (buffer)
      REMOVE uro_luse_data_quality_attribute{}.uro_data_quality_attribute_uro_appearance_src_desc_lod0{} (buffer)
      REMOVE uro_luse_data_quality_attribute{}.uro_data_quality_attribute_uro_appearance_src_desc_lod0{}.codeSpace (buffer)
      REMOVE uro_luse_data_quality_attribute{}.uro_data_quality_attribute_uro_appearance_src_desc_lod1{} (buffer)
      REMOVE uro_luse_data_quality_attribute{}.uro_data_quality_attribute_uro_appearance_src_desc_lod1{}.codeSpace (buffer)
      REMOVE uro_luse_data_quality_attribute{}.uro_data_quality_attribute_uro_appearance_src_desc_lod2{} (buffer)
      REMOVE uro_luse_data_quality_attribute{}.uro_data_quality_attribute_uro_appearance_src_desc_lod2{}.codeSpace (buffer)
      REMOVE uro_luse_data_quality_attribute{}.uro_data_quality_attribute_uro_appearance_src_desc_lod3{} (buffer)
      REMOVE uro_luse_data_quality_attribute{}.uro_data_quality_attribute_uro_appearance_src_desc_lod3{}.codeSpace (buffer)
      REMOVE uro_luse_data_quality_attribute{}.uro_data_quality_attribute_uro_appearance_src_desc_lod4{} (buffer)
      REMOVE uro_luse_data_quality_attribute{}.uro_data_quality_attribute_uro_appearance_src_desc_lod4{}.codeSpace (buffer)
      REMOVE uro_luse_data_quality_attribute{}.uro_data_quality_attribute_uro_lod_type{} (buffer)
      REMOVE uro_luse_data_quality_attribute{}.uro_data_quality_attribute_uro_lod_type{}.codeSpace (buffer)
      REMOVE uro_luse_data_quality_attribute{}.uro_data_quality_attribute_uro_lod1_height_type (buffer)
      REMOVE uro_luse_data_quality_attribute{}.uro_data_quality_attribute_uro_lod1_height_type_codeSpace (buffer)
      REMOVE uro_luse_data_quality_attribute{}.uro_data_quality_attribute_uro_tran_data_acquisition (buffer)
      REMOVE uro_luse_data_quality_attribute{}.uro_data_quality_attribute_uro_public_survey_data_quality_attribute_uro_public_survey_data_quality_attribute_uro_src_scale_lod0 (buffer)
      REMOVE uro_luse_data_quality_attribute{}.uro_data_quality_attribute_uro_public_survey_data_quality_attribute_uro_public_survey_data_quality_attribute_uro_src_scale_lod0_codeSpace (buffer)
      REMOVE uro_luse_data_quality_attribute{}.uro_data_quality_attribute_uro_public_survey_data_quality_attribute_uro_public_survey_data_quality_attribute_uro_src_scale_lod1 (buffer)
      REMOVE uro_luse_data_quality_attribute{}.uro_data_quality_attribute_uro_public_survey_data_quality_attribute_uro_public_survey_data_quality_attribute_uro_src_scale_lod1_codeSpace (buffer)
      REMOVE uro_luse_data_quality_attribute{}.uro_data_quality_attribute_uro_public_survey_data_quality_attribute_uro_public_survey_data_quality_attribute_uro_src_scale_lod2 (buffer)
      REMOVE uro_luse_data_quality_attribute{}.uro_data_quality_attribute_uro_public_survey_data_quality_attribute_uro_public_survey_data_quality_attribute_uro_src_scale_lod2_codeSpace (buffer)
      REMOVE uro_luse_data_quality_attribute{}.uro_data_quality_attribute_uro_public_survey_data_quality_attribute_uro_public_survey_data_quality_attribute_uro_src_scale_lod3 (buffer)
      REMOVE uro_luse_data_quality_attribute{}.uro_data_quality_attribute_uro_public_survey_data_quality_attribute_uro_public_survey_data_quality_attribute_uro_src_scale_lod3_codeSpace (buffer)
      REMOVE uro_luse_data_quality_attribute{}.uro_data_quality_attribute_uro_public_survey_data_quality_attribute_uro_public_survey_data_quality_attribute_uro_src_scale_lod4 (buffer)
      REMOVE uro_luse_data_quality_attribute{}.uro_data_quality_attribute_uro_public_survey_data_quality_attribute_uro_public_survey_data_quality_attribute_uro_src_scale_lod4_codeSpace (buffer)
      REMOVE uro_luse_data_quality_attribute{}.uro_data_quality_attribute_uro_public_survey_data_quality_attribute_uro_public_survey_data_quality_attribute_uro_public_survey_src_desc_lod0{} (buffer)
      REMOVE uro_luse_data_quality_attribute{}.uro_data_quality_attribute_uro_public_survey_data_quality_attribute_uro_public_survey_data_quality_attribute_uro_public_survey_src_desc_lod0{}.codeSpace (buffer)
      REMOVE uro_luse_data_quality_attribute{}.uro_data_quality_attribute_uro_public_survey_data_quality_attribute_uro_public_survey_data_quality_attribute_uro_public_survey_src_desc_lod1{} (buffer)
      REMOVE uro_luse_data_quality_attribute{}.uro_data_quality_attribute_uro_public_survey_data_quality_attribute_uro_public_survey_data_quality_attribute_uro_public_survey_src_desc_lod1{}.codeSpace (buffer)
      REMOVE uro_luse_data_quality_attribute{}.uro_data_quality_attribute_uro_public_survey_data_quality_attribute_uro_public_survey_data_quality_attribute_uro_public_survey_src_desc_lod2{} (buffer)
      REMOVE uro_luse_data_quality_attribute{}.uro_data_quality_attribute_uro_public_survey_data_quality_attribute_uro_public_survey_data_quality_attribute_uro_public_survey_src_desc_lod2{}.codeSpace (buffer)
      REMOVE uro_luse_data_quality_attribute{}.uro_data_quality_attribute_uro_public_survey_data_quality_attribute_uro_public_survey_data_quality_attribute_uro_public_survey_src_desc_lod3{} (buffer)
      REMOVE uro_luse_data_quality_attribute{}.uro_data_quality_attribute_uro_public_survey_data_quality_attribute_uro_public_survey_data_quality_attribute_uro_public_survey_src_desc_lod3{}.codeSpace (buffer)
      REMOVE uro_luse_data_quality_attribute{}.uro_data_quality_attribute_uro_public_survey_data_quality_attribute_uro_public_survey_data_quality_attribute_uro_public_survey_src_desc_lod4{} (buffer)
      REMOVE uro_luse_data_quality_attribute{}.uro_data_quality_attribute_uro_public_survey_data_quality_attribute_uro_public_survey_data_quality_attribute_uro_public_survey_src_desc_lod4{}.codeSpace (buffer)
      REMOVE uro_luse_facility_attribute{} (xml)
      REMOVE uro_luse_facility_id_attribute{}.uro_river_facility_id_attribute_uro_id (buffer)
      REMOVE uro_luse_facility_id_attribute{}.uro_river_facility_id_attribute_uro_part_id (buffer)
      REMOVE uro_luse_facility_id_attribute{}.uro_river_facility_id_attribute_uro_branch_id (buffer)
      REMOVE uro_luse_facility_id_attribute{}.uro_river_facility_id_attribute_uro_prefecture{} (buffer)
      REMOVE uro_luse_facility_id_attribute{}.uro_river_facility_id_attribute_uro_prefecture{}.codeSpace (buffer)
      REMOVE uro_luse_facility_id_attribute{}.uro_river_facility_id_attribute_uro_city{} (buffer)
      REMOVE uro_luse_facility_id_attribute{}.uro_river_facility_id_attribute_uro_city{}.codeSpace (buffer)
      REMOVE uro_luse_facility_id_attribute{}.uro_river_facility_id_attribute_uro_route (buffer)
      REMOVE uro_luse_facility_id_attribute{}.uro_river_facility_id_attribute_uro_start_post (buffer)
      REMOVE uro_luse_facility_id_attribute{}.uro_river_facility_id_attribute_uro_end_post (buffer)
      REMOVE uro_luse_facility_id_attribute{}.uro_river_facility_id_attribute_uro_start_lat (real64)
      REMOVE uro_luse_facility_id_attribute{}.uro_river_facility_id_attribute_uro_start_long (real64)
      REMOVE uro_luse_facility_id_attribute{}.uro_river_facility_id_attribute_uro_alternative_name{} (buffer)
      REMOVE uro_luse_facility_id_attribute{}.uro_river_facility_id_attribute_uro_river_code (buffer)
      REMOVE uro_luse_facility_id_attribute{}.uro_river_facility_id_attribute_uro_river_code_codeSpace (buffer)
      REMOVE uro_luse_facility_id_attribute{}.uro_river_facility_id_attribute_uro_river_name (buffer)
      REMOVE uro_luse_facility_id_attribute{}.uro_river_facility_id_attribute_uro_side_type (buffer)
      REMOVE uro_luse_facility_id_attribute{}.uro_river_facility_id_attribute_uro_side_type_codeSpace (buffer)
      REMOVE uro_luse_facility_id_attribute{}.uro_river_facility_id_attribute_uro_left_post (real64)
      REMOVE uro_luse_facility_id_attribute{}.uro_river_facility_id_attribute_uro_left_post_units (buffer)
      REMOVE uro_luse_facility_id_attribute{}.uro_river_facility_id_attribute_uro_left_distance (real64)
      REMOVE uro_luse_facility_id_attribute{}.uro_river_facility_id_attribute_uro_left_distance_units (buffer)
      REMOVE uro_luse_facility_id_attribute{}.uro_river_facility_id_attribute_uro_right_post (real64)
      REMOVE uro_luse_facility_id_attribute{}.uro_river_facility_id_attribute_uro_right_post_units (buffer)
      REMOVE uro_luse_facility_id_attribute{}.uro_river_facility_id_attribute_uro_right_distance (real64)
      REMOVE uro_luse_facility_id_attribute{}.uro_river_facility_id_attribute_uro_right_distance_units (buffer)
      REMOVE uro_luse_facility_id_attribute{}.uro_river_facility_id_attribute_uro_left_start_post (real64)
      REMOVE uro_luse_facility_id_attribute{}.uro_river_facility_id_attribute_uro_left_start_post_units (buffer)
      REMOVE uro_luse_facility_id_attribute{}.uro_river_facility_id_attribute_uro_left_start_distance (real64)
      REMOVE uro_luse_facility_id_attribute{}.uro_river_facility_id_attribute_uro_left_start_distance_units (buffer)
      REMOVE uro_luse_facility_id_attribute{}.uro_river_facility_id_attribute_uro_left_end_post (real64)
      REMOVE uro_luse_facility_id_attribute{}.uro_river_facility_id_attribute_uro_left_end_post_units (buffer)
      REMOVE uro_luse_facility_id_attribute{}.uro_river_facility_id_attribute_uro_left_end_distance (real64)
      REMOVE uro_luse_facility_id_attribute{}.uro_river_facility_id_attribute_uro_left_end_distance_units (buffer)
      REMOVE uro_luse_facility_id_attribute{}.uro_river_facility_id_attribute_uro_right_start_post (real64)
      REMOVE uro_luse_facility_id_attribute{}.uro_river_facility_id_attribute_uro_right_start_post_units (buffer)
      REMOVE uro_luse_facility_id_attribute{}.uro_river_facility_id_attribute_uro_right_start_distance (real64)
      REMOVE uro_luse_facility_id_attribute{}.uro_river_facility_id_attribute_uro_right_start_distance_units (buffer)
      REMOVE uro_luse_facility_id_attribute{}.uro_river_facility_id_attribute_uro_right_end_post (real64)
      REMOVE uro_luse_facility_id_attribute{}.uro_river_facility_id_attribute_uro_right_end_post_units (buffer)
      REMOVE uro_luse_facility_id_attribute{}.uro_river_facility_id_attribute_uro_right_end_distance (real64)
      REMOVE uro_luse_facility_id_attribute{}.uro_river_facility_id_attribute_uro_right_end_distance_units (buffer)
      REMOVE uro_luse_facility_id_attribute{}.uro_facility_id_attribute_uro_id (buffer)
      REMOVE uro_luse_facility_id_attribute{}.uro_facility_id_attribute_uro_part_id (buffer)
      REMOVE uro_luse_facility_id_attribute{}.uro_facility_id_attribute_uro_branch_id (buffer)
      REMOVE uro_luse_facility_id_attribute{}.uro_facility_id_attribute_uro_prefecture{} (buffer)
      REMOVE uro_luse_facility_id_attribute{}.uro_facility_id_attribute_uro_prefecture{}.codeSpace (buffer)
      REMOVE uro_luse_facility_id_attribute{}.uro_facility_id_attribute_uro_city{} (buffer)
      REMOVE uro_luse_facility_id_attribute{}.uro_facility_id_attribute_uro_city{}.codeSpace (buffer)
      REMOVE uro_luse_facility_id_attribute{}.uro_facility_id_attribute_uro_route (buffer)
      REMOVE uro_luse_facility_id_attribute{}.uro_facility_id_attribute_uro_start_post (buffer)
      REMOVE uro_luse_facility_id_attribute{}.uro_facility_id_attribute_uro_end_post (buffer)
      REMOVE uro_luse_facility_id_attribute{}.uro_facility_id_attribute_uro_start_lat (real64)
      REMOVE uro_luse_facility_id_attribute{}.uro_facility_id_attribute_uro_start_long (real64)
      REMOVE uro_luse_facility_id_attribute{}.uro_facility_id_attribute_uro_alternative_name{} (buffer)
      REMOVE uro_luse_facility_type_attribute{}.uro_facility_type_attribute_uro_class (buffer)
      REMOVE uro_luse_facility_type_attribute{}.uro_facility_type_attribute_uro_class_codeSpace (buffer)
      REMOVE uro_luse_facility_type_attribute{}.uro_facility_type_attribute_uro_function{} (buffer)
      REMOVE uro_luse_facility_type_attribute{}.uro_facility_type_attribute_uro_function{}.codeSpace (buffer)
      REMOVE uro_luse_key_value_pair_attribute{}.uro_key_value_pair_attribute_uro_key (buffer)
      REMOVE uro_luse_key_value_pair_attribute{}.uro_key_value_pair_attribute_uro_key_codeSpace (buffer)
      REMOVE uro_luse_key_value_pair_attribute{}.uro_key_value_pair_attribute_uro_code_value (buffer)
      REMOVE uro_luse_key_value_pair_attribute{}.uro_key_value_pair_attribute_uro_code_value_codeSpace (buffer)
      REMOVE 13+区市町村コード+大字・町コード+町・丁目コード (buffer)
      REMOVE 区市町村名称 (buffer)
      REMOVE 変化フラグ (buffer)
      REMOVE 大字・町コード (buffer)
      REMOVE 町・丁目コード  (buffer)
      REMOVE 町丁目名称 (buffer)
      REMOVE 過年度修正フラグ (buffer)
    -> Clipper_3 [CLIPPER]
Note: _landuse = road
AttributeManager_Road
    ATTR_TABLE:
      SET_TO _landuse (varchar(4)) = road
      REMOVE gml_id (buffer)
      REMOVE gml_parent_id (buffer)
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (xml)
      REMOVE externalReference{}.externalObject.uri (xml)
      REMOVE externalReference{}.informationSystem (xml)
      REMOVE citygml_generalizes_to{}.xlink_href (buffer)
      REMOVE citygml_relative_to_terrain (varchar(33))
      REMOVE citygml_relative_to_water (varchar(38))
      REMOVE citygml_appearance{}.xlink_href (buffer)
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_level_of_detail{} (buffer)
      REMOVE uro_ifc_land_use_attribute{} (xml)
      REMOVE uro_land_use_detail_attribute{}.uro_land_use_detail_attribute_uro_id (buffer)
      REMOVE uro_land_use_detail_attribute{}.uro_land_use_detail_attribute_uro_org_land_use (buffer)
      REMOVE uro_land_use_detail_attribute{}.uro_land_use_detail_attribute_uro_org_land_use_codeSpace (buffer)
      REMOVE uro_land_use_detail_attribute{}.uro_land_use_detail_attribute_uro_nominal_area (real64)
      REMOVE uro_land_use_detail_attribute{}.uro_land_use_detail_attribute_uro_nominal_area_units (buffer)
      REMOVE uro_land_use_detail_attribute{}.uro_land_use_detail_attribute_uro_owner_type (buffer)
      REMOVE uro_land_use_detail_attribute{}.uro_land_use_detail_attribute_uro_owner_type_codeSpace (buffer)
      REMOVE uro_land_use_detail_attribute{}.uro_land_use_detail_attribute_uro_owner (buffer)
      REMOVE uro_land_use_detail_attribute{}.uro_land_use_detail_attribute_uro_area_in_square_meter (real64)
      REMOVE uro_land_use_detail_attribute{}.uro_land_use_detail_attribute_uro_area_in_square_meter_units (buffer)
      REMOVE uro_land_use_detail_attribute{}.uro_land_use_detail_attribute_uro_area_in_ha (real64)
      REMOVE uro_land_use_detail_attribute{}.uro_land_use_detail_attribute_uro_area_in_ha_units (buffer)
      REMOVE uro_land_use_detail_attribute{}.uro_land_use_detail_attribute_uro_building_coverage_rate (real64)
      REMOVE uro_land_use_detail_attribute{}.uro_land_use_detail_attribute_uro_floor_area_rate (real64)
      REMOVE uro_land_use_detail_attribute{}.uro_land_use_detail_attribute_uro_specified_building_coverage_rate (real64)
      REMOVE uro_land_use_detail_attribute{}.uro_land_use_detail_attribute_uro_specified_floor_area_rate (real64)
      REMOVE uro_land_use_detail_attribute{}.uro_land_use_detail_attribute_uro_standard_floor_area_rate (real64)
      REMOVE uro_land_use_detail_attribute{}.uro_land_use_detail_attribute_uro_urban_plan_type (buffer)
      REMOVE uro_land_use_detail_attribute{}.uro_land_use_detail_attribute_uro_urban_plan_type_codeSpace (buffer)
      REMOVE uro_land_use_detail_attribute{}.uro_land_use_detail_attribute_uro_area_classification_type (buffer)
      REMOVE uro_land_use_detail_attribute{}.uro_land_use_detail_attribute_uro_area_classification_type_codeSpace (buffer)
      REMOVE uro_land_use_detail_attribute{}.uro_land_use_detail_attribute_uro_districts_and_zones_type{} (buffer)
      REMOVE uro_land_use_detail_attribute{}.uro_land_use_detail_attribute_uro_districts_and_zones_type{}.codeSpace (buffer)
      REMOVE uro_land_use_detail_attribute{}.uro_land_use_detail_attribute_uro_prefecture (buffer)
      REMOVE uro_land_use_detail_attribute{}.uro_land_use_detail_attribute_uro_prefecture_codeSpace (buffer)
      REMOVE uro_land_use_detail_attribute{}.uro_land_use_detail_attribute_uro_city (buffer)
      REMOVE uro_land_use_detail_attribute{}.uro_land_use_detail_attribute_uro_city_codeSpace (buffer)
      REMOVE uro_land_use_detail_attribute{}.uro_land_use_detail_attribute_uro_reference (buffer)
      REMOVE uro_land_use_detail_attribute{}.uro_land_use_detail_attribute_uro_note (buffer)
      REMOVE uro_land_use_detail_attribute{}.uro_land_use_detail_attribute_uro_survey_year (buffer)
      REMOVE uro_luse_data_quality_attribute{}.uro_data_quality_attribute_uro_geometry_src_desc_lod0{} (buffer)
      REMOVE uro_luse_data_quality_attribute{}.uro_data_quality_attribute_uro_geometry_src_desc_lod0{}.codeSpace (buffer)
      REMOVE uro_luse_data_quality_attribute{}.uro_data_quality_attribute_uro_geometry_src_desc_lod1{} (buffer)
      REMOVE uro_luse_data_quality_attribute{}.uro_data_quality_attribute_uro_geometry_src_desc_lod1{}.codeSpace (buffer)
      REMOVE uro_luse_data_quality_attribute{}.uro_data_quality_attribute_uro_geometry_src_desc_lod2{} (buffer)
      REMOVE uro_luse_data_quality_attribute{}.uro_data_quality_attribute_uro_geometry_src_desc_lod2{}.codeSpace (buffer)
      REMOVE uro_luse_data_quality_attribute{}.uro_data_quality_attribute_uro_geometry_src_desc_lod3{} (buffer)
      REMOVE uro_luse_data_quality_attribute{}.uro_data_quality_attribute_uro_geometry_src_desc_lod3{}.codeSpace (buffer)
      REMOVE uro_luse_data_quality_attribute{}.uro_data_quality_attribute_uro_geometry_src_desc_lod4{} (buffer)
      REMOVE uro_luse_data_quality_attribute{}.uro_data_quality_attribute_uro_geometry_src_desc_lod4{}.codeSpace (buffer)
      REMOVE uro_luse_data_quality_attribute{}.uro_data_quality_attribute_uro_thematic_src_desc{} (buffer)
      REMOVE uro_luse_data_quality_attribute{}.uro_data_quality_attribute_uro_thematic_src_desc{}.codeSpace (buffer)
      REMOVE uro_luse_data_quality_attribute{}.uro_data_quality_attribute_uro_appearance_src_desc_lod0{} (buffer)
      REMOVE uro_luse_data_quality_attribute{}.uro_data_quality_attribute_uro_appearance_src_desc_lod0{}.codeSpace (buffer)
      REMOVE uro_luse_data_quality_attribute{}.uro_data_quality_attribute_uro_appearance_src_desc_lod1{} (buffer)
      REMOVE uro_luse_data_quality_attribute{}.uro_data_quality_attribute_uro_appearance_src_desc_lod1{}.codeSpace (buffer)
      REMOVE uro_luse_data_quality_attribute{}.uro_data_quality_attribute_uro_appearance_src_desc_lod2{} (buffer)
      REMOVE uro_luse_data_quality_attribute{}.uro_data_quality_attribute_uro_appearance_src_desc_lod2{}.codeSpace (buffer)
      REMOVE uro_luse_data_quality_attribute{}.uro_data_quality_attribute_uro_appearance_src_desc_lod3{} (buffer)
      REMOVE uro_luse_data_quality_attribute{}.uro_data_quality_attribute_uro_appearance_src_desc_lod3{}.codeSpace (buffer)
      REMOVE uro_luse_data_quality_attribute{}.uro_data_quality_attribute_uro_appearance_src_desc_lod4{} (buffer)
      REMOVE uro_luse_data_quality_attribute{}.uro_data_quality_attribute_uro_appearance_src_desc_lod4{}.codeSpace (buffer)
      REMOVE uro_luse_data_quality_attribute{}.uro_data_quality_attribute_uro_lod_type{} (buffer)
      REMOVE uro_luse_data_quality_attribute{}.uro_data_quality_attribute_uro_lod_type{}.codeSpace (buffer)
      REMOVE uro_luse_data_quality_attribute{}.uro_data_quality_attribute_uro_lod1_height_type (buffer)
      REMOVE uro_luse_data_quality_attribute{}.uro_data_quality_attribute_uro_lod1_height_type_codeSpace (buffer)
      REMOVE uro_luse_data_quality_attribute{}.uro_data_quality_attribute_uro_tran_data_acquisition (buffer)
      REMOVE uro_luse_data_quality_attribute{}.uro_data_quality_attribute_uro_public_survey_data_quality_attribute_uro_public_survey_data_quality_attribute_uro_src_scale_lod0 (buffer)
      REMOVE uro_luse_data_quality_attribute{}.uro_data_quality_attribute_uro_public_survey_data_quality_attribute_uro_public_survey_data_quality_attribute_uro_src_scale_lod0_codeSpace (buffer)
      REMOVE uro_luse_data_quality_attribute{}.uro_data_quality_attribute_uro_public_survey_data_quality_attribute_uro_public_survey_data_quality_attribute_uro_src_scale_lod1 (buffer)
      REMOVE uro_luse_data_quality_attribute{}.uro_data_quality_attribute_uro_public_survey_data_quality_attribute_uro_public_survey_data_quality_attribute_uro_src_scale_lod1_codeSpace (buffer)
      REMOVE uro_luse_data_quality_attribute{}.uro_data_quality_attribute_uro_public_survey_data_quality_attribute_uro_public_survey_data_quality_attribute_uro_src_scale_lod2 (buffer)
      REMOVE uro_luse_data_quality_attribute{}.uro_data_quality_attribute_uro_public_survey_data_quality_attribute_uro_public_survey_data_quality_attribute_uro_src_scale_lod2_codeSpace (buffer)
      REMOVE uro_luse_data_quality_attribute{}.uro_data_quality_attribute_uro_public_survey_data_quality_attribute_uro_public_survey_data_quality_attribute_uro_src_scale_lod3 (buffer)
      REMOVE uro_luse_data_quality_attribute{}.uro_data_quality_attribute_uro_public_survey_data_quality_attribute_uro_public_survey_data_quality_attribute_uro_src_scale_lod3_codeSpace (buffer)
      REMOVE uro_luse_data_quality_attribute{}.uro_data_quality_attribute_uro_public_survey_data_quality_attribute_uro_public_survey_data_quality_attribute_uro_src_scale_lod4 (buffer)
      REMOVE uro_luse_data_quality_attribute{}.uro_data_quality_attribute_uro_public_survey_data_quality_attribute_uro_public_survey_data_quality_attribute_uro_src_scale_lod4_codeSpace (buffer)
      REMOVE uro_luse_data_quality_attribute{}.uro_data_quality_attribute_uro_public_survey_data_quality_attribute_uro_public_survey_data_quality_attribute_uro_public_survey_src_desc_lod0{} (buffer)
      REMOVE uro_luse_data_quality_attribute{}.uro_data_quality_attribute_uro_public_survey_data_quality_attribute_uro_public_survey_data_quality_attribute_uro_public_survey_src_desc_lod0{}.codeSpace (buffer)
      REMOVE uro_luse_data_quality_attribute{}.uro_data_quality_attribute_uro_public_survey_data_quality_attribute_uro_public_survey_data_quality_attribute_uro_public_survey_src_desc_lod1{} (buffer)
      REMOVE uro_luse_data_quality_attribute{}.uro_data_quality_attribute_uro_public_survey_data_quality_attribute_uro_public_survey_data_quality_attribute_uro_public_survey_src_desc_lod1{}.codeSpace (buffer)
      REMOVE uro_luse_data_quality_attribute{}.uro_data_quality_attribute_uro_public_survey_data_quality_attribute_uro_public_survey_data_quality_attribute_uro_public_survey_src_desc_lod2{} (buffer)
      REMOVE uro_luse_data_quality_attribute{}.uro_data_quality_attribute_uro_public_survey_data_quality_attribute_uro_public_survey_data_quality_attribute_uro_public_survey_src_desc_lod2{}.codeSpace (buffer)
      REMOVE uro_luse_data_quality_attribute{}.uro_data_quality_attribute_uro_public_survey_data_quality_attribute_uro_public_survey_data_quality_attribute_uro_public_survey_src_desc_lod3{} (buffer)
      REMOVE uro_luse_data_quality_attribute{}.uro_data_quality_attribute_uro_public_survey_data_quality_attribute_uro_public_survey_data_quality_attribute_uro_public_survey_src_desc_lod3{}.codeSpace (buffer)
      REMOVE uro_luse_data_quality_attribute{}.uro_data_quality_attribute_uro_public_survey_data_quality_attribute_uro_public_survey_data_quality_attribute_uro_public_survey_src_desc_lod4{} (buffer)
      REMOVE uro_luse_data_quality_attribute{}.uro_data_quality_attribute_uro_public_survey_data_quality_attribute_uro_public_survey_data_quality_attribute_uro_public_survey_src_desc_lod4{}.codeSpace (buffer)
      REMOVE uro_luse_facility_attribute{} (xml)
      REMOVE uro_luse_facility_id_attribute{}.uro_river_facility_id_attribute_uro_id (buffer)
      REMOVE uro_luse_facility_id_attribute{}.uro_river_facility_id_attribute_uro_part_id (buffer)
      REMOVE uro_luse_facility_id_attribute{}.uro_river_facility_id_attribute_uro_branch_id (buffer)
      REMOVE uro_luse_facility_id_attribute{}.uro_river_facility_id_attribute_uro_prefecture{} (buffer)
      REMOVE uro_luse_facility_id_attribute{}.uro_river_facility_id_attribute_uro_prefecture{}.codeSpace (buffer)
      REMOVE uro_luse_facility_id_attribute{}.uro_river_facility_id_attribute_uro_city{} (buffer)
      REMOVE uro_luse_facility_id_attribute{}.uro_river_facility_id_attribute_uro_city{}.codeSpace (buffer)
      REMOVE uro_luse_facility_id_attribute{}.uro_river_facility_id_attribute_uro_route (buffer)
      REMOVE uro_luse_facility_id_attribute{}.uro_river_facility_id_attribute_uro_start_post (buffer)
      REMOVE uro_luse_facility_id_attribute{}.uro_river_facility_id_attribute_uro_end_post (buffer)
      REMOVE uro_luse_facility_id_attribute{}.uro_river_facility_id_attribute_uro_start_lat (real64)
      REMOVE uro_luse_facility_id_attribute{}.uro_river_facility_id_attribute_uro_start_long (real64)
      REMOVE uro_luse_facility_id_attribute{}.uro_river_facility_id_attribute_uro_alternative_name{} (buffer)
      REMOVE uro_luse_facility_id_attribute{}.uro_river_facility_id_attribute_uro_river_code (buffer)
      REMOVE uro_luse_facility_id_attribute{}.uro_river_facility_id_attribute_uro_river_code_codeSpace (buffer)
      REMOVE uro_luse_facility_id_attribute{}.uro_river_facility_id_attribute_uro_river_name (buffer)
      REMOVE uro_luse_facility_id_attribute{}.uro_river_facility_id_attribute_uro_side_type (buffer)
      REMOVE uro_luse_facility_id_attribute{}.uro_river_facility_id_attribute_uro_side_type_codeSpace (buffer)
      REMOVE uro_luse_facility_id_attribute{}.uro_river_facility_id_attribute_uro_left_post (real64)
      REMOVE uro_luse_facility_id_attribute{}.uro_river_facility_id_attribute_uro_left_post_units (buffer)
      REMOVE uro_luse_facility_id_attribute{}.uro_river_facility_id_attribute_uro_left_distance (real64)
      REMOVE uro_luse_facility_id_attribute{}.uro_river_facility_id_attribute_uro_left_distance_units (buffer)
      REMOVE uro_luse_facility_id_attribute{}.uro_river_facility_id_attribute_uro_right_post (real64)
      REMOVE uro_luse_facility_id_attribute{}.uro_river_facility_id_attribute_uro_right_post_units (buffer)
      REMOVE uro_luse_facility_id_attribute{}.uro_river_facility_id_attribute_uro_right_distance (real64)
      REMOVE uro_luse_facility_id_attribute{}.uro_river_facility_id_attribute_uro_right_distance_units (buffer)
      REMOVE uro_luse_facility_id_attribute{}.uro_river_facility_id_attribute_uro_left_start_post (real64)
      REMOVE uro_luse_facility_id_attribute{}.uro_river_facility_id_attribute_uro_left_start_post_units (buffer)
      REMOVE uro_luse_facility_id_attribute{}.uro_river_facility_id_attribute_uro_left_start_distance (real64)
      REMOVE uro_luse_facility_id_attribute{}.uro_river_facility_id_attribute_uro_left_start_distance_units (buffer)
      REMOVE uro_luse_facility_id_attribute{}.uro_river_facility_id_attribute_uro_left_end_post (real64)
      REMOVE uro_luse_facility_id_attribute{}.uro_river_facility_id_attribute_uro_left_end_post_units (buffer)
      REMOVE uro_luse_facility_id_attribute{}.uro_river_facility_id_attribute_uro_left_end_distance (real64)
      REMOVE uro_luse_facility_id_attribute{}.uro_river_facility_id_attribute_uro_left_end_distance_units (buffer)
      REMOVE uro_luse_facility_id_attribute{}.uro_river_facility_id_attribute_uro_right_start_post (real64)
      REMOVE uro_luse_facility_id_attribute{}.uro_river_facility_id_attribute_uro_right_start_post_units (buffer)
      REMOVE uro_luse_facility_id_attribute{}.uro_river_facility_id_attribute_uro_right_start_distance (real64)
      REMOVE uro_luse_facility_id_attribute{}.uro_river_facility_id_attribute_uro_right_start_distance_units (buffer)
      REMOVE uro_luse_facility_id_attribute{}.uro_river_facility_id_attribute_uro_right_end_post (real64)
      REMOVE uro_luse_facility_id_attribute{}.uro_river_facility_id_attribute_uro_right_end_post_units (buffer)
      REMOVE uro_luse_facility_id_attribute{}.uro_river_facility_id_attribute_uro_right_end_distance (real64)
      REMOVE uro_luse_facility_id_attribute{}.uro_river_facility_id_attribute_uro_right_end_distance_units (buffer)
      REMOVE uro_luse_facility_id_attribute{}.uro_facility_id_attribute_uro_id (buffer)
      REMOVE uro_luse_facility_id_attribute{}.uro_facility_id_attribute_uro_part_id (buffer)
      REMOVE uro_luse_facility_id_attribute{}.uro_facility_id_attribute_uro_branch_id (buffer)
      REMOVE uro_luse_facility_id_attribute{}.uro_facility_id_attribute_uro_prefecture{} (buffer)
      REMOVE uro_luse_facility_id_attribute{}.uro_facility_id_attribute_uro_prefecture{}.codeSpace (buffer)
      REMOVE uro_luse_facility_id_attribute{}.uro_facility_id_attribute_uro_city{} (buffer)
      REMOVE uro_luse_facility_id_attribute{}.uro_facility_id_attribute_uro_city{}.codeSpace (buffer)
      REMOVE uro_luse_facility_id_attribute{}.uro_facility_id_attribute_uro_route (buffer)
      REMOVE uro_luse_facility_id_attribute{}.uro_facility_id_attribute_uro_start_post (buffer)
      REMOVE uro_luse_facility_id_attribute{}.uro_facility_id_attribute_uro_end_post (buffer)
      REMOVE uro_luse_facility_id_attribute{}.uro_facility_id_attribute_uro_start_lat (real64)
      REMOVE uro_luse_facility_id_attribute{}.uro_facility_id_attribute_uro_start_long (real64)
      REMOVE uro_luse_facility_id_attribute{}.uro_facility_id_attribute_uro_alternative_name{} (buffer)
      REMOVE uro_luse_facility_type_attribute{}.uro_facility_type_attribute_uro_class (buffer)
      REMOVE uro_luse_facility_type_attribute{}.uro_facility_type_attribute_uro_class_codeSpace (buffer)
      REMOVE uro_luse_facility_type_attribute{}.uro_facility_type_attribute_uro_function{} (buffer)
      REMOVE uro_luse_facility_type_attribute{}.uro_facility_type_attribute_uro_function{}.codeSpace (buffer)
      REMOVE uro_luse_key_value_pair_attribute{}.uro_key_value_pair_attribute_uro_key (buffer)
      REMOVE uro_luse_key_value_pair_attribute{}.uro_key_value_pair_attribute_uro_key_codeSpace (buffer)
      REMOVE uro_luse_key_value_pair_attribute{}.uro_key_value_pair_attribute_uro_code_value (buffer)
      REMOVE uro_luse_key_value_pair_attribute{}.uro_key_value_pair_attribute_uro_code_value_codeSpace (buffer)
      REMOVE 13+区市町村コード+大字・町コード+町・丁目コード (buffer)
      REMOVE 区市町村名称 (buffer)
      REMOVE 変化フラグ (buffer)
      REMOVE 大字・町コード (buffer)
      REMOVE 町・丁目コード  (buffer)
      REMOVE 町丁目名称 (buffer)
      REMOVE 過年度修正フラグ (buffer)
    -> Clipper_3 [CLIPPER]
Note: シミュレーション範囲 / [OGCGEOPACKAGE]
parsed (reader OGCGEOPACKAGE_1)
    attributes: felt:feature int, felt:has_geometry boolean, felt:h3_index int, felt:geometry_size int, felt:color text, felt:fillOpacity double, felt:id text, felt:locked int, felt:ordering int, felt:showArea int, felt:strokeOpacity int, felt:strokeStyle text, felt:strokeWidth int, felt:type text, gpkg_fid int,PrimaryKey
    -> CsmapReprojector
CsmapReprojector
    DEST = $(DEST_COORDSYS)
    INTERPOLATION_TYPE_NAME = NearestNeighbor
    RASTER_CELL_SIZE = PreserveCells
    RASTER_TOLERANCE = 0.0
    SOURCE = EPSG:6668
    REPROJECTED -> Clipper_2 [CLIPPER]
Note: シミュレーション範囲を抽出
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_3 [CANDIDATE]
Note: 水面、道路、その他に分割
Clipper_3
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Junction_4
    OUTSIDE -> AttributeCreator
Junction_4
    -> Junction_5
Junction_5
    -> Triangulator
Note: _landuse = ground
AttributeCreator
    ATTR_TABLE = SET_TO _landuse (varchar(6)) = ground
    INPUT_PORT_CONNECTED = CONNECTED
    -> Triangulator
Note: シミュレーション範囲境界、土地利用区分境界で分割された面は三角形でなくなったりマルチエリアになったりするので、三角形分割、デアグリゲートしてすべて単一の三角形とする。
Triangulator
    DEAGGREGATE_INPUT = Deaggregate
    TRIANGLES -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = Yes
    DEAGGREGATED -> Junction_11
Note: Snapper : Input
Junction_11
    -> Junction_12
Note: Deaggregator : Deaggregated
Junction_12
    -> Snapper
Snapper
    EXTEND_LINES = NEVER
    SAVE_SHORT_LINES = No
    SNAPTYPE = VERTEX
    SNAP_3D = Yes
    TOLERANCE = 0.01
    SNAPPED -> Junction
    UNTOUCHED -> Junction
Junction
    -> Junction_8
    -> Dissolver
Junction_6
    -> Junction_7
Junction_7
    -> FeatureMerger [REQUESTOR]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter
Offsetter
    MODE_LOOKUP = CARTESIAN
    XOFF = @Value(x_offset)
    YOFF = @Value(y_offset)
    ZOFF = @Value(z_offset)
    MODE = Cartesian Coordinate
    OFFSET -> MeshMerger
    OFFSET -> NewFeatureType (writer STL_1)
NewFeatureType (writer STL_1)
skirt (writer STL_1)
offset_values (writer CSV2_1)
    attributes: x_offset real64, y_offset real64, z_offset real64

Bookmark: PLATEAU 地形モデル
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
ReliefFeature (reader CITYGML_1)
    attributes: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
TINRelief (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer
    -> Tester

Bookmark: PLATEAU 土地利用モデル
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
LandUse (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, uro_ifc_land_use_attribute{} xml_xml, uro_land_use_detail_attribute{}.uro_land_use_detail_attribute_uro_id xml_buffer, uro_land_use_detail_attribute{}.uro_land_use_detail_attribute_uro_org_land_use xml_buffer, uro_land_use_detail_attribute{}.uro_land_use_detail_attribute_uro_org_land_use_codeSpace xml_buffer, uro_land_use_detail_attribute{}.uro_land_use_detail_attribute_uro_nominal_area xml_real64, uro_land_use_detail_attribute{}.uro_land_use_detail_attribute_uro_nominal_area_units xml_buffer, uro_land_use_detail_attribute{}.uro_land_use_detail_attribute_uro_owner_type xml_buffer, uro_land_use_detail_attribute{}.uro_land_use_detail_attribute_uro_owner_type_codeSpace xml_buffer,
      uro_land_use_detail_attribute{}.uro_land_use_detail_attribute_uro_owner xml_buffer, uro_land_use_detail_attribute{}.uro_land_use_detail_attribute_uro_area_in_square_meter xml_real64, uro_land_use_detail_attribute{}.uro_land_use_detail_attribute_uro_area_in_square_meter_units xml_buffer, uro_land_use_detail_attribute{}.uro_land_use_detail_attribute_uro_area_in_ha xml_real64, uro_land_use_detail_attribute{}.uro_land_use_detail_attribute_uro_area_in_ha_units xml_buffer, uro_land_use_detail_attribute{}.uro_land_use_detail_attribute_uro_building_coverage_rate xml_real64, uro_land_use_detail_attribute{}.uro_land_use_detail_attribute_uro_floor_area_rate xml_real64, uro_land_use_detail_attribute{}.uro_land_use_detail_attribute_uro_specified_building_coverage_rate xml_real64, uro_land_use_detail_attribute{}.uro_land_use_detail_attribute_uro_specified_floor_area_rate xml_real64, uro_land_use_detail_attribute{}.uro_land_use_detail_attribute_uro_standard_floor_area_rate xml_real64, uro_land_use_detail_attribute{}.uro_land_use_detail_attribute_uro_urban_plan_type xml_buffer, uro_land_use_detail_attribute{}.uro_land_use_detail_attribute_uro_urban_plan_type_codeSpace xml_buffer, uro_land_use_detail_attribute{}.uro_land_use_detail_attribute_uro_area_classification_type xml_buffer, uro_land_use_detail_attribute{}.uro_land_use_detail_attribute_uro_area_classification_type_codeSpace xml_buffer, uro_land_use_detail_attribute{}.uro_land_use_detail_attribute_uro_districts_and_zones_type{} xml_buffer, uro_land_use_detail_attribute{}.uro_land_use_detail_attribute_uro_districts_and_zones_type{}.codeSpace xml_buffer, uro_land_use_detail_attribute{}.uro_land_use_detail_attribute_uro_prefecture xml_buffer, uro_land_use_detail_attribute{}.uro_land_use_detail_attribute_uro_prefecture_codeSpace xml_buffer, uro_land_use_detail_attribute{}.uro_land_use_detail_attribute_uro_city xml_buffer, uro_land_use_detail_attribute{}.uro_land_use_detail_attribute_uro_city_codeSpace xml_buffer, uro_land_use_detail_attribute{}.uro_land_use_detail_attribute_uro_reference xml_buffer, uro_land_use_detail_attribute{}.uro_land_use_detail_attribute_uro_note xml_buffer, uro_land_use_detail_attribute{}.uro_land_use_detail_attribute_uro_survey_year xml_buffer, uro_luse_data_quality_attribute{}.uro_data_quality_attribute_uro_geometry_src_desc_lod0{} xml_buffer, uro_luse_data_quality_attribute{}.uro_data_quality_attribute_uro_geometry_src_desc_lod0{}.codeSpace xml_buffer, uro_luse_data_quality_attribute{}.uro_data_quality_attribute_uro_geometry_src_desc_lod1{} xml_buffer, uro_luse_data_quality_attribute{}.uro_data_quality_attribute_uro_geometry_src_desc_lod1{}.codeSpace xml_buffer, uro_luse_data_quality_attribute{}.uro_data_quality_attribute_uro_geometry_src_desc_lod2{} xml_buffer, uro_luse_data_quality_attribute{}.uro_data_quality_attribute_uro_geometry_src_desc_lod2{}.codeSpace xml_buffer, uro_luse_data_quality_attribute{}.uro_data_quality_attribute_uro_geometry_src_desc_lod3{} xml_buffer,
      uro_luse_data_quality_attribute{}.uro_data_quality_attribute_uro_geometry_src_desc_lod3{}.codeSpace xml_buffer, uro_luse_data_quality_attribute{}.uro_data_quality_attribute_uro_geometry_src_desc_lod4{} xml_buffer, uro_luse_data_quality_attribute{}.uro_data_quality_attribute_uro_geometry_src_desc_lod4{}.codeSpace xml_buffer, uro_luse_data_quality_attribute{}.uro_data_quality_attribute_uro_thematic_src_desc{} xml_buffer, uro_luse_data_quality_attribute{}.uro_data_quality_attribute_uro_thematic_src_desc{}.codeSpace xml_buffer, uro_luse_data_quality_attribute{}.uro_data_quality_attribute_uro_appearance_src_desc_lod0{} xml_buffer, uro_luse_data_quality_attribute{}.uro_data_quality_attribute_uro_appearance_src_desc_lod0{}.codeSpace xml_buffer, uro_luse_data_quality_attribute{}.uro_data_quality_attribute_uro_appearance_src_desc_lod1{} xml_buffer, uro_luse_data_quality_attribute{}.uro_data_quality_attribute_uro_appearance_src_desc_lod1{}.codeSpace xml_buffer, uro_luse_data_quality_attribute{}.uro_data_quality_attribute_uro_appearance_src_desc_lod2{} xml_buffer, uro_luse_data_quality_attribute{}.uro_data_quality_attribute_uro_appearance_src_desc_lod2{}.codeSpace xml_buffer, uro_luse_data_quality_attribute{}.uro_data_quality_attribute_uro_appearance_src_desc_lod3{} xml_buffer, uro_luse_data_quality_attribute{}.uro_data_quality_attribute_uro_appearance_src_desc_lod3{}.codeSpace xml_buffer, uro_luse_data_quality_attribute{}.uro_data_quality_attribute_uro_appearance_src_desc_lod4{} xml_buffer, uro_luse_data_quality_attribute{}.uro_data_quality_attribute_uro_appearance_src_desc_lod4{}.codeSpace xml_buffer, uro_luse_data_quality_attribute{}.uro_data_quality_attribute_uro_lod_type{} xml_buffer, uro_luse_data_quality_attribute{}.uro_data_quality_attribute_uro_lod_type{}.codeSpace xml_buffer, uro_luse_data_quality_attribute{}.uro_data_quality_attribute_uro_lod1_height_type xml_buffer, uro_luse_data_quality_attribute{}.uro_data_quality_attribute_uro_lod1_height_type_codeSpace xml_buffer, uro_luse_data_quality_attribute{}.uro_data_quality_attribute_uro_tran_data_acquisition xml_buffer, uro_luse_data_quality_attribute{}.uro_data_quality_attribute_uro_public_survey_data_quality_attribute_uro_public_survey_data_quality_attribute_uro_src_scale_lod0 xml_buffer, uro_luse_data_quality_attribute{}.uro_data_quality_attribute_uro_public_survey_data_quality_attribute_uro_public_survey_data_quality_attribute_uro_src_scale_lod0_codeSpace xml_buffer, uro_luse_data_quality_attribute{}.uro_data_quality_attribute_uro_public_survey_data_quality_attribute_uro_public_survey_data_quality_attribute_uro_src_scale_lod1 xml_buffer, uro_luse_data_quality_attribute{}.uro_data_quality_attribute_uro_public_survey_data_quality_attribute_uro_public_survey_data_quality_attribute_uro_src_scale_lod1_codeSpace xml_buffer, uro_luse_data_quality_attribute{}.uro_data_quality_attribute_uro_public_survey_data_quality_attribute_uro_public_survey_data_quality_attribute_uro_src_scale_lod2 xml_buffer, uro_luse_data_quality_attribute{}.uro_data_quality_attribute_uro_public_survey_data_quality_attribute_uro_public_survey_data_quality_attribute_uro_src_scale_lod2_codeSpace xml_buffer, uro_luse_data_quality_attribute{}.uro_data_quality_attribute_uro_public_survey_data_quality_attribute_uro_public_survey_data_quality_attribute_uro_src_scale_lod3 xml_buffer, uro_luse_data_quality_attribute{}.uro_data_quality_attribute_uro_public_survey_data_quality_attribute_uro_public_survey_data_quality_attribute_uro_src_scale_lod3_codeSpace xml_buffer, uro_luse_data_quality_attribute{}.uro_data_quality_attribute_uro_public_survey_data_quality_attribute_uro_public_survey_data_quality_attribute_uro_src_scale_lod4 xml_buffer, uro_luse_data_quality_attribute{}.uro_data_quality_attribute_uro_public_survey_data_quality_attribute_uro_public_survey_data_quality_attribute_uro_src_scale_lod4_codeSpace xml_buffer,
      uro_luse_data_quality_attribute{}.uro_data_quality_attribute_uro_public_survey_data_quality_attribute_uro_public_survey_data_quality_attribute_uro_public_survey_src_desc_lod0{} xml_buffer, uro_luse_data_quality_attribute{}.uro_data_quality_attribute_uro_public_survey_data_quality_attribute_uro_public_survey_data_quality_attribute_uro_public_survey_src_desc_lod0{}.codeSpace xml_buffer, uro_luse_data_quality_attribute{}.uro_data_quality_attribute_uro_public_survey_data_quality_attribute_uro_public_survey_data_quality_attribute_uro_public_survey_src_desc_lod1{} xml_buffer, uro_luse_data_quality_attribute{}.uro_data_quality_attribute_uro_public_survey_data_quality_attribute_uro_public_survey_data_quality_attribute_uro_public_survey_src_desc_lod1{}.codeSpace xml_buffer, uro_luse_data_quality_attribute{}.uro_data_quality_attribute_uro_public_survey_data_quality_attribute_uro_public_survey_data_quality_attribute_uro_public_survey_src_desc_lod2{} xml_buffer, uro_luse_data_quality_attribute{}.uro_data_quality_attribute_uro_public_survey_data_quality_attribute_uro_public_survey_data_quality_attribute_uro_public_survey_src_desc_lod2{}.codeSpace xml_buffer, uro_luse_data_quality_attribute{}.uro_data_quality_attribute_uro_public_survey_data_quality_attribute_uro_public_survey_data_quality_attribute_uro_public_survey_src_desc_lod3{} xml_buffer, uro_luse_data_quality_attribute{}.uro_data_quality_attribute_uro_public_survey_data_quality_attribute_uro_public_survey_data_quality_attribute_uro_public_survey_src_desc_lod3{}.codeSpace xml_buffer, uro_luse_data_quality_attribute{}.uro_data_quality_attribute_uro_public_survey_data_quality_attribute_uro_public_survey_data_quality_attribute_uro_public_survey_src_desc_lod4{} xml_buffer, uro_luse_data_quality_attribute{}.uro_data_quality_attribute_uro_public_survey_data_quality_attribute_uro_public_survey_data_quality_attribute_uro_public_survey_src_desc_lod4{}.codeSpace xml_buffer, uro_luse_facility_attribute{} xml_xml, uro_luse_facility_id_attribute{}.uro_river_facility_id_attribute_uro_id xml_buffer, uro_luse_facility_id_attribute{}.uro_river_facility_id_attribute_uro_part_id xml_buffer, uro_luse_facility_id_attribute{}.uro_river_facility_id_attribute_uro_branch_id xml_buffer, uro_luse_facility_id_attribute{}.uro_river_facility_id_attribute_uro_prefecture{} xml_buffer, uro_luse_facility_id_attribute{}.uro_river_facility_id_attribute_uro_prefecture{}.codeSpace xml_buffer, uro_luse_facility_id_attribute{}.uro_river_facility_id_attribute_uro_city{} xml_buffer, uro_luse_facility_id_attribute{}.uro_river_facility_id_attribute_uro_city{}.codeSpace xml_buffer, uro_luse_facility_id_attribute{}.uro_river_facility_id_attribute_uro_route xml_buffer, uro_luse_facility_id_attribute{}.uro_river_facility_id_attribute_uro_start_post xml_buffer, uro_luse_facility_id_attribute{}.uro_river_facility_id_attribute_uro_end_post xml_buffer, uro_luse_facility_id_attribute{}.uro_river_facility_id_attribute_uro_start_lat xml_real64, uro_luse_facility_id_attribute{}.uro_river_facility_id_attribute_uro_start_long xml_real64, uro_luse_facility_id_attribute{}.uro_river_facility_id_attribute_uro_alternative_name{} xml_buffer, uro_luse_facility_id_attribute{}.uro_river_facility_id_attribute_uro_river_code xml_buffer, uro_luse_facility_id_attribute{}.uro_river_facility_id_attribute_uro_river_code_codeSpace xml_buffer, uro_luse_facility_id_attribute{}.uro_river_facility_id_attribute_uro_river_name xml_buffer, uro_luse_facility_id_attribute{}.uro_river_facility_id_attribute_uro_side_type xml_buffer, uro_luse_facility_id_attribute{}.uro_river_facility_id_attribute_uro_side_type_codeSpace xml_buffer, uro_luse_facility_id_attribute{}.uro_river_facility_id_attribute_uro_left_post xml_real64,
      uro_luse_facility_id_attribute{}.uro_river_facility_id_attribute_uro_left_post_units xml_buffer, uro_luse_facility_id_attribute{}.uro_river_facility_id_attribute_uro_left_distance xml_real64, uro_luse_facility_id_attribute{}.uro_river_facility_id_attribute_uro_left_distance_units xml_buffer, uro_luse_facility_id_attribute{}.uro_river_facility_id_attribute_uro_right_post xml_real64, uro_luse_facility_id_attribute{}.uro_river_facility_id_attribute_uro_right_post_units xml_buffer, uro_luse_facility_id_attribute{}.uro_river_facility_id_attribute_uro_right_distance xml_real64, uro_luse_facility_id_attribute{}.uro_river_facility_id_attribute_uro_right_distance_units xml_buffer, uro_luse_facility_id_attribute{}.uro_river_facility_id_attribute_uro_left_start_post xml_real64, uro_luse_facility_id_attribute{}.uro_river_facility_id_attribute_uro_left_start_post_units xml_buffer, uro_luse_facility_id_attribute{}.uro_river_facility_id_attribute_uro_left_start_distance xml_real64, uro_luse_facility_id_attribute{}.uro_river_facility_id_attribute_uro_left_start_distance_units xml_buffer, uro_luse_facility_id_attribute{}.uro_river_facility_id_attribute_uro_left_end_post xml_real64, uro_luse_facility_id_attribute{}.uro_river_facility_id_attribute_uro_left_end_post_units xml_buffer, uro_luse_facility_id_attribute{}.uro_river_facility_id_attribute_uro_left_end_distance xml_real64, uro_luse_facility_id_attribute{}.uro_river_facility_id_attribute_uro_left_end_distance_units xml_buffer, uro_luse_facility_id_attribute{}.uro_river_facility_id_attribute_uro_right_start_post xml_real64, uro_luse_facility_id_attribute{}.uro_river_facility_id_attribute_uro_right_start_post_units xml_buffer, uro_luse_facility_id_attribute{}.uro_river_facility_id_attribute_uro_right_start_distance xml_real64, uro_luse_facility_id_attribute{}.uro_river_facility_id_attribute_uro_right_start_distance_units xml_buffer, uro_luse_facility_id_attribute{}.uro_river_facility_id_attribute_uro_right_end_post xml_real64, uro_luse_facility_id_attribute{}.uro_river_facility_id_attribute_uro_right_end_post_units xml_buffer, uro_luse_facility_id_attribute{}.uro_river_facility_id_attribute_uro_right_end_distance xml_real64, uro_luse_facility_id_attribute{}.uro_river_facility_id_attribute_uro_right_end_distance_units xml_buffer, uro_luse_facility_id_attribute{}.uro_facility_id_attribute_uro_id xml_buffer, uro_luse_facility_id_attribute{}.uro_facility_id_attribute_uro_part_id xml_buffer, uro_luse_facility_id_attribute{}.uro_facility_id_attribute_uro_branch_id xml_buffer, uro_luse_facility_id_attribute{}.uro_facility_id_attribute_uro_prefecture{} xml_buffer, uro_luse_facility_id_attribute{}.uro_facility_id_attribute_uro_prefecture{}.codeSpace xml_buffer, uro_luse_facility_id_attribute{}.uro_facility_id_attribute_uro_city{} xml_buffer, uro_luse_facility_id_attribute{}.uro_facility_id_attribute_uro_city{}.codeSpace xml_buffer,
      uro_luse_facility_id_attribute{}.uro_facility_id_attribute_uro_route xml_buffer, uro_luse_facility_id_attribute{}.uro_facility_id_attribute_uro_start_post xml_buffer, uro_luse_facility_id_attribute{}.uro_facility_id_attribute_uro_end_post xml_buffer, uro_luse_facility_id_attribute{}.uro_facility_id_attribute_uro_start_lat xml_real64, uro_luse_facility_id_attribute{}.uro_facility_id_attribute_uro_start_long xml_real64, uro_luse_facility_id_attribute{}.uro_facility_id_attribute_uro_alternative_name{} xml_buffer, uro_luse_facility_type_attribute{}.uro_facility_type_attribute_uro_class xml_buffer, uro_luse_facility_type_attribute{}.uro_facility_type_attribute_uro_class_codeSpace xml_buffer, uro_luse_facility_type_attribute{}.uro_facility_type_attribute_uro_function{} xml_buffer, uro_luse_facility_type_attribute{}.uro_facility_type_attribute_uro_function{}.codeSpace xml_buffer, uro_luse_key_value_pair_attribute{}.uro_key_value_pair_attribute_uro_key xml_buffer, uro_luse_key_value_pair_attribute{}.uro_key_value_pair_attribute_uro_key_codeSpace xml_buffer, uro_luse_key_value_pair_attribute{}.uro_key_value_pair_attribute_uro_code_value xml_buffer, uro_luse_key_value_pair_attribute{}.uro_key_value_pair_attribute_uro_code_value_codeSpace xml_buffer, 13+区市町村コード+大字・町コード+町・丁目コード xml_buffer, 区市町村名称 xml_buffer, 変化フラグ xml_buffer, 大字・町コード xml_buffer, 町・丁目コード  xml_buffer, 町丁目名称 xml_buffer, 過年度修正フラグ xml_buffer
    -> 2DForcer

Bookmark: 三角形を同じ土地利用が連担している範囲ごとに集約し, Mesh サーフェスに変換
Dissolver
    ACCUM_INPUT_ATTRS_LOOKUP = None
    CLEANING_TOLERANCE_LOOKUP = AUTO
    CONNECT_Z_MODE_LOOKUP = FIRST_WINS
    DEAGGREGATE_INPUT = Yes
    GROUP_BY = _landuse
    ACCUM_INPUT_ATTRS = Drop Incoming Attributes
    CLEANING_TOLERANCE = Automatic
    CONNECT_Z_MODE = First Wins
    AREA -> Counter
Counter
    CNT_ATTR = _temp_id
    DOMAIN = counter
    SCOPE = Global
    START = 0
    -> SpatialFilter [Filter]
Junction_8
    -> Junction_9
Junction_9
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> FaceReplacer
Note: Polygon -> Face
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> Aggregator
Note: Faces -> MultiSurface
Aggregator
    ACCUM_ATTRS = None
    AGGREGATE_TYPE = Homogeneous Collection (If Possible)
    GROUP_BY = _landuse _temp_id
    MODE = Geometry - Assemble One Level
    SEP = ,
    AGGREGATE -> GeometryCoercer
Note: -> CompositeSurface
GeometryCoercer
    GQUERY:
      for $geom in //geometry
      where $geom/count(parent::geometry) = 0
      return number($geom/@fme_id)
    KIND = fme_composite_surface
    COERCED -> GeometryCoercer_2
Note: -> Mesh
GeometryCoercer_2
    GQUERY:
      for $geom in //geometry
      where $geom/count(parent::geometry) = 0
      return number($geom/@fme_id)
    KIND = fme_mesh
    COERCED -> BoundsExtractor
    COERCED -> Junction_6

Bookmark: オフセット量計算
BoundsExtractor
    XMAX = _xmax
    XMIN = _xmin
    YMAX = _ymax
    YMIN = _ymin
    ZMAX = _zmax
    ZMIN = _zmin
    -> StatisticsCalculator
StatisticsCalculator
    ATTR_ACCUM_MODE = None
    CALCULATION_MODE = NUMERIC
    FEAT_STATS = _xmin,NUMERIC_MODE,MIN,,,,,,,,,,,,;_ymin,NUMERIC_MODE,MIN,,,,,,,,,,,,;_zmin,NUMERIC_MODE,MIN,,,,,,,,,,,,
    SUMMARY -> AttributeManager
AttributeManager
    ATTR_TABLE:
      RENAME_SET_VALUE _xmin.min > x_offset (real64) = @Evaluate(@CurrentAttribute()<1 ? 1-@CurrentAttribute() : 0)
      RENAME_SET_VALUE _ymin.min > y_offset (real64) = @Evaluate(@CurrentAttribute()<1 ? 1-@CurrentAttribute() : 0)
      RENAME_SET_VALUE _zmin.min > z_offset (real64) = @Evaluate(@CurrentAttribute()<2 ? 2-@CurrentAttribute() : 0)
    -> AttributeRounder
AttributeRounder
    PLACES = 0
    ROUND_TYPE_TCL = ceil
    SRC_ATTRS = x_offset y_offset z_offset
    ROUND_TYPE = Up
    -> FeatureMerger [SUPPLIER]
    -> offset_values (writer CSV2_1)

Bookmark: z=1 平面からシミュレーション範囲外周の地形高さまでの鉛直面
MeshMerger
    ACCUM_INPUT_ATTRS_LOOKUP = None
    ACCUM_INPUT_ATTRS = Drop Incoming Attributes
    MESH -> BRepSolidBoundaryCreator.Beta [Surface]
BRepSolidBoundaryCreator.Beta
    ELEVATION = 1
    Side -> skirt (writer STL_1)

FME custom transformer BRepSolidBoundaryCreator.Beta
Creates a planar surface representing the orthogonal projection of the source surface, and a ring-shaped vertical sidewall surface that bridges between the boundaries of the planar surface and the source surface. The resulting surfaces can be used to build a boundary representation solid (IFMEBRepSolid). 
    This transformer accepts features having a surface geometry except aggregate and multi-surface. If the input feature geometry is not acceptable, it will be output via the <Rejected> port. 
    Note: This transformer is a tech preview regarding surface manipulation with Python FME Objects API. It may be removed from the FME Hub if a regular transformer having a functionality equivalent to this transformer would be introduced in the future.
    Usage Note
    This transformer assumes that the source surface represents a single consecutive shape oriented to Z positive direction, and the boundary of the source surface is equal to the boundary of the orthogonal projection (i.e. the source surface is NOT folded). Otherwise, the translation could be aborted with an error or the resulting surfaces may not form a topologically clean solid. 
    You can transform an aggregate of surfaces which are output from this transformer into a boundary representation solid (IFMEBrepSolid) or a composite surface (IFMECompositeSurface), using an Aggregator and a GeometryCoercer transformer (Geometry Type: fme_brep_solid or fme_composite_surface).
    Output Ports 
    Top
    : 
    If the elevation which is specified through the "Planar Surface Elevation" parameter is less than the MINIMUM Z of the source surface, the source surface will be output via this port without any transformation. If the specified elevation is greater than the MAXIMUM Z of the source surface, a planar surface representing the orthogonal projection of the source surface will be output via this port.
    Side
    :
    A composite surface forming a ring-shaped vertical sidewall that bridges between the boundaries of the Top surface and the Bottom surface will be output via this port.
    Bottom
    :
    If the elevation which is specified through the "Planar Surface Elevation" parameter is less than the MINIMUM Z of the source surface, the planar surface representing the orthogonal projection of the source surface will be output via this port. If the specified elevation is greater than the MAXIMUM Z of the source surface, the source surface whose orientation is reversed will be output via this port.
Parameters
    Planar Surface Elevation
    :
    Specify the elevation of the planar surface which should be created as an orthogonal projection of the source surface. The value must be less than the MINIMUM Z, or greater than the MAXIMUM Z of the source surface. Otherwise, the input feature will be output via the <Rejected> port.

Parameters:
- ELEVATION =   # Planar Surface Elevation

Surface (input)
    -> AggregateFilter
AggregateFilter
    AGGREGATE -> AttributeCreator_3
    NOT_AGGREGATE -> GeometryFilter
GeometryFilter
    BREAK_AGG_BOOL = 0
    GEOM_PORTS = SURFACE
    BREAK_AGG = No
    GEOM_PORT_NAMES = Surface
    SURFACE -> BoundsExtractor
    <UNFILTERED> -> AttributeCreator_3
BoundsExtractor
    ZMAX = __ssc.zmax
    ZMIN = __ssc.zmin
    -> AttributeCreator
AttributeCreator
    ATTR_TABLE:
      SET_TO __ssc.elevation = $(ELEVATION)
      SET_TO __ssc.flag = FME_CONDITIONAL:DEFAULT_VALUE'0'BOOL_OP;OR;COMPOSITE_TEST;<Unused>;TEST $(ELEVATION) < @Value(__ssc.zmin)'-1'BOOL_OP;OR;COMPOSITE_TEST;<Unused>;TEST @Value(__ssc.zmax) < $(ELEVATION)'1'FME_NUM_CONDITIONS3___
    -> Tester
Tester
    BOOL_OP = OR
    TEST_CLAUSE = TEST @Value(__ssc.flag) != 0
    TEST_MODE = Automatic
    PASSED -> Counter
    FAILED -> AttributeCreator_2
Counter
    CNT_ATTR = __ssc.id
    DOMAIN = counter_id
    SCOPE = Local
    START = 0
    SCOPEVAR = Local
    -> Tester_2
    -> PythonCaller
Tester_2
    BOOL_OP = OR
    TEST_CLAUSE = TEST @Value(__ssc.flag) < 0
    TEST_MODE = Automatic
    PASSED -> Tester_3_PASSED
    FAILED -> Orientor
Note: Top
Tester_3_PASSED: Junction
    -> Top_2
Top_2: Junction
    -> Top (output)
Orientor
    FLIP_APPEARANCES_LOOKUP = FLIP_APPEARANCES
    KIND = REVERSE
    FLIP_APPEARANCES_CHOICE = Yes
    ORIENTED -> Tester_3_FAILED
Note: Bottom
Tester_3_FAILED: Junction
    -> Bottom_2
Bottom_2: Junction
    -> Bottom (output)
PythonCaller
    NEW_ATTRIBUTES = __ssc.id
    PYTHONSOURCE:
      # 2016-09-16, Takashi Iijima, Original Implementation

      import fme
      import fmeobjects

      class OutershellChopper(object):
          def input(self, feature):
              flag = int(feature.getAttribute('__ssc.flag'))
              self.chopped = []
              self.chop(feature.getGeometry())
              segs = {}
              for line in self.chopped:
                  coords = sorted([p.getXYZ() for p in line.getPoints()])
                  segs.setdefault((coords[0], coords[1]), []).append(line)
              for line in [s[0] for s in segs.values() if len(s) == 1]:
                  if flag < 0:
                      line.reverse()
                  feature.setGeometry(line)
                  self.pyoutput(feature)

          def chop(self, surface):
              if isinstance(surface, fmeobjects.FMEFace):
                  self.chopped += surface.getAsWireFrame()
              elif isinstance(surface, fmeobjects.FMEMesh):
                  self.chopped += surface.getAsWireFrame()
              elif isinstance(surface, fmeobjects.FMERectangleFace):
                  self.chop(surface.getAsFaceCopy())
              elif isinstance(surface, fmeobjects.FMETriangleFan):
                  for i in range(surface.numParts()):
                      self.chop(surface.getAsFaceAt(i))
              elif isinstance(surface, fmeobjects.FMETriangleStrip):
                  for i in range(surface.numParts()):
                      self.chop(surface.getAsFaceAt(i))
              elif isinstance(surface, fmeobjects.FMECompositeSurface):
                  for i in range(surface.numParts()):
                      self.chop(surface.getPartAt(i))
    PYTHONSYMBOL = OutershellChopper
    -> LineJoiner
LineJoiner
    ACCUM_ATTRS = ONE
    CLOSE = yes
    CONSIDER_NODE_ELEVATION_LOOKUP = YES
    GROUP_BY = __ssc.id
    LINES_AS_SEGMENTS = Yes
    NODED = END_NODED
    PRESERVE = yes
    ACCUM_ATTRS_NAME = Get Attributes From One Representative Feature
    BREAK = no
    CONSIDER_NODE_ELEVATION = yes
    TOPOLOGY = End noded
    LINE -> Counter_2
Counter_2
    CNT_ATTR = __ssc.part_id
    DOMAIN = counter_part_id
    SCOPE = Local
    START = 0
    SCOPEVAR = Local
    -> PathSplitter
PathSplitter
    -> PythonCaller_2
PythonCaller_2
    NEW_ATTRIBUTES = __ssc.type
    PYTHONSOURCE:
      # 2016-09-16: Takashi Iijima, Original Implementation

      import fme
      import fmeobjects
      class BRepSolidBoundaryCreator(object):
          def __init__(self):
              self.wallFaces = {}
              self.planarBoundaries = {}
              self.prevId = None
              self.feature = None

          def input(self, feature):
              id = feature.getAttribute('__ssc.id')
              if id != self.prevId:
                  self.outputSurface()
                  self.wallFaces = {}
                  self.planarBoundaries = {}
                  self.prevId = id
              partId = feature.getAttribute('__ssc.part_id')
              if partId not in self.wallFaces:
                  self.wallFaces[partId] = []
                  self.planarBoundaries[partId] = []
              v0 = feature.getCoordinate(0)
              v1 = feature.getCoordinate(1)
              if v0[0] != v1[0] or v0[1] != v1[1]:
                  z = float(feature.getAttribute('__ssc.elevation'))
                  v2 = (v1[0], v1[1], z)
                  v3 = (v0[0], v0[1], z)
                  boundary = fmeobjects.FMELine([v0, v1, v2, v3, v0])
                  self.wallFaces[partId].append(fmeobjects.FMEFace(boundary, fmeobjects.FME_CLOSE_3D_AVERAGE_MODE))
                  self.planarBoundaries[partId].append(v2)
                  self.feature = feature

          def close(self):
              self.outputSurface()

          def outputSurface(self):
              for partId in sorted(self.wallFaces.keys()):
                  wallFaces = self.wallFaces[partId]
                  planarBoundaries = self.planarBoundaries[partId]
                  if wallFaces:
                      sidewall = fmeobjects.FMECompositeSurface()
                      for face in wallFaces:
                          sidewall.appendPart(face)
                      self.feature.setGeometry(sidewall)
                      self.feature.setAttribute('__ssc.type', 'side')
                      self.pyoutput(self.feature)

                      planarBoundaries.append(planarBoundaries[0])
                      planar = fmeobjects.FMEPolygon(fmeobjects.FMELine(planarBoundaries))
                      self.feature.setGeometry(planar)
                      self.feature.setAttribute('__ssc.type', 'planar')
                      self.pyoutput(self.feature)
    PYTHONSYMBOL = BRepSolidBoundaryCreator
    -> Tester_3
Tester_3
    BOOL_OP = OR
    TEST_CLAUSE = TEST @Value(__ssc.type) = side
    TEST_MODE = Automatic
    PASSED -> Side (output)
    FAILED -> DonutBuilder
Side (output)
DonutBuilder
    ALLOW_CYCLES = No
    CONNECT_Z_MODE_LOOKUP = FIRST_WINS
    GROUP_BY = __ssc.id
    TAG_HOLES = NO
    CONNECT_Z_MODE = First Wins
    DROP = yes
    AREA -> FaceReplacer
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> Tester_4
Tester_4
    BOOL_OP = OR
    TEST_CLAUSE = TEST 0 < @Value(__ssc.flag)
    TEST_MODE = Automatic
    PASSED -> Top (output)
    FAILED -> Bottom (output)
Top (output)
Bottom (output)
AttributeCreator_2
    ATTR_TABLE = SET_TO _rejected_reason = specified elevation is within zmin and zmax of seed surface
    -> <Rejected> (output)
AttributeCreator_3
    ATTR_TABLE = SET_TO _rejected_reason = unsupported geometry type
    -> <Rejected> (output)
<Rejected> (output)
